-- NBAP-IEs.asn
--
-- Taken from 3GPP TS 25.433 V9.2.0 (2010-03)
-- http://www.3gpp.org/ftp/Specs/archive/25_series/25.433/
--
-- 9.3.4	Information Elements Definitions
--
-- $Id: NBAP-IEs.asn 52132 2013-09-18 02:48:29Z cmaynard $
--

--******************************************************************************
--
-- Information Element Definitions
--
--******************************************************************************

NBAP-IEs {
itu-t (0) identified-organization (4) etsi (0) mobileDomain (0)
umts-Access (20) modules (3) nbap (2) version1 (1) nbap-IEs (2) }

DEFINITIONS AUTOMATIC TAGS ::=
BEGIN

IMPORTS
	maxNrOfRLs,
	maxNrOfTFCs,
	maxNrOfErrors,
	maxCTFC,
	maxNrOfTFs,
	maxTTI-count,
	maxRateMatching,
	maxHS-PDSCHCodeNrComp-1,
	maxHS-SCCHCodeNrComp-1,
	maxNrOfCellSyncBursts,
	maxNrOfCombEDPDCH,
	maxNrOfEDCH-HARQ-PO-QUANTSTEPs,
	maxNrOfEDCHHARQProcesses2msEDCH,
	maxNrOfBits-MACe-PDU-non-scheduled,
	maxNrOfEDPCCH-PO-QUANTSTEPs,
	maxNrOfRefETFCI-PO-QUANTSTEPs,
	maxNrOfRefETFCIs,
	maxNrOfMeasNCell,
	maxNrOfMeasNCell-1,
	maxNrOfReceptsPerSyncFrame,
	maxNrOfSF,
	maxTGPS,
	maxNrOfUSCHs,
	maxNrOfULTSs,
	maxNrOfULTSLCRs,
	maxNrOfDPCHs,
	maxNrOfDPCHLCRs,
	maxNrOfDPCHs768,
	maxNrOfCodes,
	maxNrOfDSCHs,
	maxNrOfDLTSs,
	maxNrOfDLTSLCRs,
	maxNrOfDCHs,
	maxNrOfLevels,
	maxNoGPSItems,
	maxNoSat,
	maxNrOfCellPortionsPerCell,
	maxNrOfCellPortionsPerCell-1,
	maxNrOfHSSCCHs,
	maxNrOfHSSCCHCodes,
	maxNrOfMACdFlows,
	maxNrOfMACdFlows-1,
	maxNrOfMACdPDUIndexes,
	maxNrOfMACdPDUIndexes-1,
	maxNrOfMACdPDUSize,
	maxNrOfNIs,
	maxNrOfPriorityQueues,
	maxNrOfPriorityQueues-1,
	maxNrOfHARQProcesses,
	maxNrOfSyncDLCodesLCR,
	maxNrOfSyncFramesLCR,
	maxNrOfContextsOnUeList,
	maxNrOfPriorityClasses,
	maxNrOfSatAlmanac-maxNoSat,
	maxNrOfE-AGCHs,
	maxNrOfEDCHMACdFlows,
	maxNrOfEDCHMACdFlows-1,
	maxNrOfE-RGCHs-E-HICHs,
	maxNrofSigSeqRGHI-1,
	maxNoOfLogicalChannels,
	maxNrOfEAGCHs,
	maxNrOfRefBetas,
	maxNrOfEAGCHCodes,
	maxNrOfHS-DSCH-TBSs,
	maxNrOfHS-DSCH-TBSs-HS-SCCHless,
	maxNrOfEHICHCodes,
	maxNrOfCommonMACFlows,
	maxNrOfCommonMACFlows-1,
	maxNrOfPagingMACFlow,
	maxNrOfPagingMACFlow-1,
	maxNrOfcommonMACQueues,
	maxNrOfpagingMACQueues,
	maxNrOfHS-DSCHTBSsE-PCH,
	maxGANSSSat,
	maxNoGANSS,
	maxSgnType,
	maxHSDPAFrequency,
	maxHSDPAFrequency-1,
	maxGANSSSatAlmanac,
	maxGANSSClockMod,
	maxNrOfEDCHRLs,
	maxCellinNodeB,
	maxERNTItoRelease,
	maxNrOfCommonEDCH,
	maxFrequencyinCell-1,
	maxNrOfCommonMACFlowsLCR,
	maxNrOfCommonMACFlowsLCR-1,
	maxNrOfHSSCCHsLCR,
	maxNrOfEDCHMACdFlowsLCR,
	maxNrOfEDCHMACdFlowsLCR-1,
	maxNrOfEAGCHsLCR,
	maxNrOfEHICHsLCR,
	maxnrofERUCCHsLCR,
	maxNrOfHSPDSCHs,
	maxFrequencyinCell,
	maxNrOfHSDSCH-1,
	maxNrOfHSDSCH,
	maxGANSS-1,
	maxNoOfTBSs-Mapping-HS-DSCH-SPS,
	maxNoOfTBSs-Mapping-HS-DSCH-SPS-1,
	maxNoOfHS-DSCH-TBSsLCR,
	maxNoOfRepetition-Period-LCR,
	maxNoOfRepetitionPeriod-SPS-LCR-1,
	maxNoOf-HS-SICH-SPS,
	maxNoOf-HS-SICH-SPS-1,
	maxNoOfNon-HS-SCCH-Assosiated-HS-SICH,
	maxNoOfNon-HS-SCCH-Assosiated-HS-SICH-Ext,
	maxMBMSServiceSelect,
	maxNrOfCellPortionsPerCellLCR,
	maxNrOfCellPortionsPerCellLCR-1,
	maxNrOfEDCH-1,
 	maxNoOfCommonH-RNTI,
	maxNrOfCommonMACFlowsLCRExt,
	maxofERNTI,
	maxNrOfDCHMeasurementOccasionPatternSequence,

	id-BroadcastCommonTransportBearerIndication,
	id-MessageStructure,
	id-ReportCharacteristicsType-OnModification,
	id-Rx-Timing-Deviation-Value-LCR,
	id-SFNSFNMeasurementValueInformation,
	id-SFNSFNMeasurementThresholdInformation,
	id-TUTRANGPSMeasurementValueInformation,
	id-TUTRANGPSMeasurementThresholdInformation,
	id-TypeOfError,
	id-transportlayeraddress,
	id-bindingID,
	id-Angle-Of-Arrival-Value-LCR,
	id-SyncDLCodeIdThreInfoLCR,
	id-neighbouringTDDCellMeasurementInformationLCR,
	id-HS-SICH-Reception-Quality,
	id-HS-SICH-Reception-Quality-Measurement-Value,
	id-Initial-DL-Power-TimeslotLCR-InformationItem,
	id-Maximum-DL-Power-TimeslotLCR-InformationItem,
	id-Minimum-DL-Power-TimeslotLCR-InformationItem,
	id-Received-total-wide-band-power-For-CellPortion,
	id-Received-total-wide-band-power-For-CellPortion-Value,
	id-Transmitted-Carrier-Power-For-CellPortion,
	id-Transmitted-Carrier-Power-For-CellPortion-Value,
	id-TransmittedCarrierPowerOfAllCodesNotUsedForHSTransmission,
	id-TransmittedCarrierPowerOfAllCodesNotUsedForHS-PDSCH-HS-SCCH-E-AGCH-E-RGCHOrE-HICHTransmissionCellPortion,
	id-TransmittedCarrierPowerOfAllCodesNotUsedForHS-PDSCH-HS-SCCH-E-AGCH-E-RGCHOrE-HICHTransmissionCellPortionValue,
	id-HS-DSCHRequiredPowerValueInformation,
	id-HS-DSCHProvidedBitRateValueInformation,
	id-HS-DSCHRequiredPowerValue,
	id-HS-DSCHRequiredPowerValue-For-Cell-Portion,
	id-HS-DSCHRequiredPowerValueInformation-For-CellPortion,
	id-HS-DSCHProvidedBitRateValueInformation-For-CellPortion,
	id-HSDSCH-MACdPDUSizeFormat,
	id-HS-PDSCH-Code-Change-Grant,
	id-HS-PDSCH-Code-Change-Indicator,
	id-HS-DSCH-SPS-Operation-Indicator,
	id-Best-Cell-Portions-Value,
	id-Unidirectional-DCH-Indicator,
	id-SAT-Info-Almanac-ExtItem,
	id-TnlQos,
	id-UpPTSInterferenceValue,
	id-HARQ-Preamble-Mode,
	id-HARQ-Preamble-Mode-Activation-Indicator,
	id-DLTransmissionBranchLoadValue,
	id-E-DCHProvidedBitRateValueInformation,
	id-E-DCH-Non-serving-Relative-Grant-Down-CommandsValue,
	id-HSSICH-SIRTarget,
	id-PLCCH-Information-UL-TimeslotLCR-Info,
	id-neighbouringTDDCellMeasurementInformation768,
	id-Rx-Timing-Deviation-Value-768,
	id-hsSCCH-Specific-Information-ResponseTDD768,
	id-Rx-Timing-Deviation-Value-384-ext,
	id-E-DCH-PowerOffset-for-SchedulingInfo,
	id-Extended-Round-Trip-Time-Value,
	id-ExtendedPropagationDelay,
	id-HSSICH-TPC-StepSize,
	id-RTWP-CellPortion-ReportingIndicator,
	id-Received-Scheduled-EDCH-Power-Share-Value,
	id-Received-Scheduled-EDCH-Power-Share-For-CellPortion-Value,
	id-Received-Scheduled-EDCH-Power-Share,
	id-Received-Scheduled-EDCH-Power-Share-For-CellPortion,
	id-ueCapability-Info,
	id-ContinuousPacketConnectivityHS-SCCH-less-Information,
	id-ContinuousPacketConnectivityHS-SCCH-less-Information-Response,
	id-MIMO-ActivationIndicator,
	id-MIMO-Mode-Indicator,
	id-MIMO-N-M-Ratio,
	id-Additional-failed-HS-SICH,
	id-Additional-missed-HS-SICH,
	id-Additional-total-HS-SICH,
	id-Additional-HS-SICH-Reception-Quality-Measurement-Value,
	id-LCRTDD-uplink-Physical-Channel-Capability,
	id-SixteenQAM-UL-Operation-Indicator,
	id-E-AGCH-Table-Choice,
	id-E-TFCI-Boost-Information,
	id-E-DPDCH-PowerInterpolation,
	id-MaximumMACdPDU-SizeExtended,
	id-GANSS-Common-Data,
	id-GANSS-Information,
	id-GANSS-Generic-Data,
	id-TUTRANGANSSMeasurementThresholdInformation,
	id-TUTRANGANSSMeasurementValueInformation,
	id-Extended-RNC-ID,
	id-HARQ-MemoryPartitioningInfoExtForMIMO,
	id-Ext-Reference-E-TFCI-PO,
	id-Ext-Max-Bits-MACe-PDU-non-scheduled,
	id-TransportBearerNotSetupIndicator,
	id-TransportBearerNotRequestedIndicator,
	id-UARFCNforNt,
	id-number-Of-Supported-Carriers,
	id-multipleFreq-HSPDSCH-InformationList-ResponseTDDLCR,
	id-tSN-Length,
	id-multicarrier-number,
	id-Extended-HS-SICH-ID,
	id-Default-Serving-Grant-in-DTX-Cycle2,
	id-SixtyfourQAM-UsageAllowedIndicator,
	id-SixtyfourQAM-DL-UsageIndicator,
	id-IPMulticastDataBearerIndication,
	id-Extended-E-DCH-LCRTDD-PhysicalLayerCategory,
	id-ContinuousPacketConnectivityHS-SCCH-less-Deactivate-Indicator,
	id-Extended-E-HICH-ID-TDD,
	id-E-DCH-MACdPDUSizeFormat,
	id-MaximumNumber-Of-Retransmission-for-Scheduling-Info-LCRTDD,
	id-E-DCH-RetransmissionTimer-for-SchedulingInfo-LCRTDD,
	id-E-PUCH-PowerControlGAP,
	id-HSDSCH-TBSizeTableIndicator,
	id-E-DCH-DL-Control-Channel-Change-Information,
	id-E-DCH-DL-Control-Channel-Grant-Information,
	id-DGANSS-Corrections-Req,
	id-UE-with-enhanced-HS-SCCH-support-indicator,
	id-TransportBearerRequestIndicator,
	id-EnhancedHSServingCC-Abort,
	id-GANSS-Time-ID,
	id-GANSS-AddIonoModelReq,
	id-GANSS-EarthOrientParaReq,
	id-GANSS-AddNavigationModelsReq,
	id-GANSS-AddUTCModelsReq,
	id-GANSS-AuxInfoReq,
	id-GANSS-SBAS-ID,
	id-GANSS-ID,
	id-GANSS-Additional-Ionospheric-Model,
	id-GANSS-Earth-Orientation-Parameters,
	id-GANSS-Additional-Time-Models,
	id-GANSS-Additional-Navigation-Models,
	id-GANSS-Additional-UTC-Models,
	id-GANSS-Auxiliary-Information,
	id-GANSS-alm-keplerianNAVAlmanac,
	id-GANSS-alm-keplerianReducedAlmanac,
	id-GANSS-alm-keplerianMidiAlmanac,
	id-GANSS-alm-keplerianGLONASS,
	id-GANSS-alm-ecefSBASAlmanac,
	id-EDCH-RACH-Report-Value,
	id-EDCH-RACH-Report-IncrDecrThres,
	id-EDCH-RACH-Report-ThresholdInformation,
	id-MACes-Maximum-Bitrate-LCR,
	id-E-AGCH-UE-Inactivity-Monitor-Threshold,
	id-MultiCarrier-HSDSCH-Physical-Layer-Category,
	id-MIMO-ReferenceSignal-InformationListLCR,
	id-MIMO-SFMode-For-HSPDSCHDualStream,
	id-MIMO-SFMode-Supported-For-HSPDSCHDualStream,
	id-DL-RLC-PDU-Size-Format,
	id-schedulingPriorityIndicator,
	id-UE-SupportIndicatorExtension,
	id-UE-AggregateMaximumBitRate-Enforcement-Indicator,
	id-Single-Stream-MIMO-ActivationIndicator,
	id-Single-Stream-MIMO-Mode-Indicator,
	id-TransmittedCarrierPowerOfAllCodesNotUsedForHS-PDSCH-HS-SCCH-E-AGCHOrE-HICHTransmissionCellPortion,
	id-ULTimeslotISCPValue-For-CellPortion,
	id-UpPTSInterferenceValue-For-CellPortion,
	id-Best-Cell-Portions-ValueLCR,
	id-Transmitted-Carrier-Power-For-CellPortion-ValueLCR,
	id-Received-total-wide-band-power-For-CellPortion-ValueLCR,
	id-TransmittedCarrierPowerOfAllCodesNotUsedForHS-PDSCH-HS-SCCH-E-AGCHOrE-HICHTransmissionCellPortionValue,
	id-UL-TimeslotISCP-For-CellPortion-Value,
	id-HS-DSCHRequiredPowerValueInformation-For-CellPortionLCR,
	id-HS-DSCHProvidedBitRateValueInformation-For-CellPortionLCR,
	id-E-DCHProvidedBitRateValueInformation-For-CellPortion,
	id-UpPTSInterference-For-CellPortion-Value,
	id-HS-DSCH-SPS-Reservation-Indicator,
	id-E-DCH-SPS-Reservation-Indicator,
	id-MultipleFreq-HARQ-MemoryPartitioning-InformationList,
	id-DiversityMode,
	id-TransmitDiversityIndicator,
	id-NonCellSpecificTxDiversity,
	id-RepetitionPeriodIndex,
	id-MidambleShiftLCR,
	id-MaxHSDSCH-HSSCCH-Power-per-CELLPORTION,
	id-Additional-EDCH-Preconfiguration-Information,
	id-EDCH-Indicator,
	id-Ul-common-E-DCH-MACflow-Specific-InfoResponseListLCR-Ext,
	id-E-RNTI-List-Request,
	id-E-RNTI-List,
	id-UL-Synchronisation-Parameters-For-FACHLCR,
	id-UE-TS0-CapabilityLCR,
	id-Add-To-Non-HS-SCCH-Associated-HS-SICH-Resource-Pool-LCR-PSCH-ReconfRqst-Ext,
	id-Modify-Non-HS-SCCH-Associated-HS-SICH-Resource-Pool-LCR-PSCH-ReconfRqst-Ext,
	id-DGNSS-ValidityPeriod,
	id-AssociatedPhsicalChannelID,
	id-PhysicalChannelID-for-CommonERNTI-RequestedIndicator,
	id-Initial-DL-Transmission-Power,
	id-Maximum-DL-Power,
	id-Minimum-DL-Power,
	id-Multicell-EDCH-InformationItemIEs,
	id-Multicell-EDCH-RL-Specific-InformationItemIEs



FROM NBAP-Constants

	Criticality,
	ProcedureID,
	ProtocolIE-ID,
	TransactionID,
	TriggeringMessage
FROM NBAP-CommonDataTypes

	NBAP-PROTOCOL-IES,
	ProtocolExtensionContainer{},
	ProtocolIE-Single-Container{},
	NBAP-PROTOCOL-EXTENSION
FROM NBAP-Containers;

-- ==========================================
--	A
-- ==========================================

AckNack-RepetitionFactor ::= INTEGER (1..4,...)
-- Step: 1

Ack-Power-Offset ::= INTEGER (0..8,...)
-- According to mapping in ref. [9] subclause 4.2.1

Acknowledged-PRACH-preambles-Value ::= INTEGER(0..240,...)
-- According to mapping in [22].

ActivationInformation ::= SEQUENCE (SIZE (1..maxNrOfEDCH-1)) OF ActivationInformationItem

ActivationInformationItem ::= SEQUENCE {
	uU-ActivationState	Uu-ActivationState,
	iE-Extensions									ProtocolExtensionContainer { { ActivationInformationItem-ExtIEs} }				OPTIONAL,
	...
}

ActivationInformationItem-ExtIEs NBAP-PROTOCOL-EXTENSION ::= {
	...
}

Additional-EDCH-Setup-Info	::=SEQUENCE{
	multicell-EDCH-Transport-Bearer-Mode									Multicell-EDCH-Transport-Bearer-Mode,
	additional-EDCH-Cell-Information-Setup									Additional-EDCH-Cell-Information-Setup,
	iE-Extensions					ProtocolExtensionContainer { { Additional-EDCH-Setup-Info-ExtIEs} } OPTIONAL,
	...
}

Additional-EDCH-Setup-Info-ExtIEs	NBAP-PROTOCOL-EXTENSION ::= {
	...
}

Multicell-EDCH-Transport-Bearer-Mode ::= ENUMERATED {
	separate-Iub-Transport-Bearer-Mode,
	uL-Flow-Multiplexing-Mode
}


Additional-EDCH-Cell-Information-Setup	::= SEQUENCE (SIZE (1..maxNrOfEDCH-1)) OF Additional-EDCH-FDD-Setup-Cell-Information

Additional-EDCH-FDD-Setup-Cell-Information	::=SEQUENCE{
	additional-EDCH-UL-DPCH-Information-Setup						Additional-EDCH-UL-DPCH-Information-Setup,
	additional-EDCH-RL-Specific-Information-To-Setup				Additional-EDCH-RL-Specific-Information-To-Setup-List,
	additional-EDCH-FDD-Information									Additional-EDCH-FDD-Information		OPTIONAL,
	additional-EDCH-F-DPCH-Information-Setup						Additional-EDCH-F-DPCH-Information,
	multicell-EDCH-Information										Multicell-EDCH-Information			OPTIONAL,
	iE-Extensions					ProtocolExtensionContainer { { Additional-EDCH-FDD-Setup-Cell-Information-ExtIEs} } OPTIONAL,
	...
}

Additional-EDCH-FDD-Setup-Cell-Information-ExtIEs	NBAP-PROTOCOL-EXTENSION ::= {
	...
}

Additional-EDCH-UL-DPCH-Information-Setup	::=SEQUENCE{
	ul-ScramblingCode						UL-ScramblingCode,
	ul-SIR-Target							UL-SIR,
	iE-Extensions					ProtocolExtensionContainer { { Additional-EDCH-UL-DPCH-Information-Setup-ExtIEs} } OPTIONAL,
	...
}

Additional-EDCH-UL-DPCH-Information-Setup-ExtIEs	NBAP-PROTOCOL-EXTENSION ::= {
	...
}

Additional-EDCH-F-DPCH-Information	::=SEQUENCE{
	fdd-TPC-DownlinkStepSize			FDD-TPC-DownlinkStepSize,
	limitedPowerIncrease				LimitedPowerIncrease,
	innerLoopDLPCStatus					InnerLoopDLPCStatus,
	iE-Extensions					ProtocolExtensionContainer { { Additional-EDCH-F-DPCH-Information-ExtIEs} } OPTIONAL,
	...
}

Additional-EDCH-F-DPCH-Information-ExtIEs	NBAP-PROTOCOL-EXTENSION ::= {
	...
}

Additional-EDCH-RL-Specific-Information-To-Setup-List	::= SEQUENCE (SIZE (1..maxNrOfEDCHRLs)) OF Additional-EDCH-RL-Specific-Information-To-Setup-ItemIEs


Additional-EDCH-RL-Specific-Information-To-Setup-ItemIEs	::=SEQUENCE{
	eDCH-Additional-RL-ID				RL-ID,
	c-ID								C-ID										OPTIONAL,
	firstRLS-indicator					FirstRLS-Indicator,
	propagationDelay					PropagationDelay							OPTIONAL,
	dl-CodeInformation					FDD-DL-CodeInformation,
	initialDL-transmissionPower			DL-Power,
	maximumDL-power						DL-Power,
	minimumDL-power						DL-Power,
	f-DPCH-SlotFormat					F-DPCH-SlotFormat 							OPTIONAL,
	e-RNTI								E-RNTI 										OPTIONAL,
	multicell-EDCH-RL-Specific-Information	Multicell-EDCH-RL-Specific-Information	OPTIONAL,
	iE-Extensions						ProtocolExtensionContainer { { Additional-EDCH-RL-Specific-Information-To-Setup-ItemIEs-ExtIEs} } OPTIONAL,
	...
}

Additional-EDCH-RL-Specific-Information-To-Setup-ItemIEs-ExtIEs	NBAP-PROTOCOL-EXTENSION ::= {
	...
}

Additional-EDCH-Cell-Information-To-Add-List	::= SEQUENCE (SIZE (1..maxNrOfEDCH-1)) OF Additional-EDCH-Cell-Information-To-Add-ItemIEs

Additional-EDCH-Cell-Information-To-Add-ItemIEs	::=SEQUENCE{
	additional-EDCH-RL-Specific-Information-To-Add-ItemIEs	Additional-EDCH-RL-Specific-Information-To-Add-ItemIEs,
	additional-EDCH-FDD-Information							Additional-EDCH-FDD-Information			OPTIONAL,
	multicell-EDCH-Information								Multicell-EDCH-Information				OPTIONAL,
	iE-Extensions						ProtocolExtensionContainer { { Additional-EDCH-Cell-Information-To-Add-ItemIEs-ExtIEs} } OPTIONAL,
	...
}

Additional-EDCH-Cell-Information-To-Add-ItemIEs-ExtIEs	NBAP-PROTOCOL-EXTENSION ::= {
	...
}

Additional-EDCH-RL-Specific-Information-To-Add-ItemIEs	::= SEQUENCE (SIZE (1.. maxNrOfEDCHRLs)) OF EDCH-Additional-RL-Specific-Information-To-Add-List

EDCH-Additional-RL-Specific-Information-To-Add-List	::=SEQUENCE{
	eDCH-Additional-RL-ID				RL-ID,
	c-ID								C-ID,
	dl-CodeInformation					FDD-DL-CodeInformation,
	initialDL-transmissionPower			DL-Power				OPTIONAL,
	maximumDL-power						DL-Power				OPTIONAL,
	minimumDL-power						DL-Power				OPTIONAL,
	f-DPCH-SlotFormat					F-DPCH-SlotFormat 		OPTIONAL,
	multicell-EDCH-RL-Specific-Information	Multicell-EDCH-RL-Specific-Information 		OPTIONAL,
	iE-Extensions						ProtocolExtensionContainer { { EDCH-Additional-RL-Specific-Information-To-Add-List-ExtIEs} } OPTIONAL,
	...
}

EDCH-Additional-RL-Specific-Information-To-Add-List-ExtIEs	NBAP-PROTOCOL-EXTENSION ::= {
	...
}

Additional-EDCH-RL-Specific-Information-To-Modify-List	::= SEQUENCE (SIZE (1..maxNrOfEDCHRLs)) OF Additional-EDCH-RL-Specific-Information-To-Modify-ItemIEs

Additional-EDCH-RL-Specific-Information-To-Modify-ItemIEs	::=SEQUENCE{
	eDCH-Additional-RL-ID				RL-ID,
	dl-CodeInformation					FDD-DL-CodeInformation 	OPTIONAL,
	maximumDL-power						DL-Power				OPTIONAL,
	minimumDL-power						DL-Power				OPTIONAL,
	f-DPCH-SlotFormat					F-DPCH-SlotFormat 		OPTIONAL,

	multicell-EDCH-RL-Specific-Information		Multicell-EDCH-RL-Specific-Information 	OPTIONAL,	iE-Extensions						ProtocolExtensionContainer { { Additional-EDCH-RL-Specific-Information-To-Modify-ItemIEs-ExtIEs} } OPTIONAL,
	...
}

Additional-EDCH-RL-Specific-Information-To-Modify-ItemIEs-ExtIEs	NBAP-PROTOCOL-EXTENSION ::= {
	...
}

Additional-EDCH-FDD-Information	::=SEQUENCE{
	additional-EDCH-MAC-d-Flows-Specific-Information	Additional-EDCH-MAC-d-Flows-Specific-Info-List	OPTIONAL,
	hARQ-Process-Allocation-Scheduled-2ms-EDCH		HARQ-Process-Allocation-2ms-EDCH				OPTIONAL,
	e-DCH-Maximum-Bitrate							E-DCH-Maximum-Bitrate							OPTIONAL,
	e-DCH-Processing-Overload-Level					E-DCH-Processing-Overload-Level					OPTIONAL,
	e-DCH-Min-Set-E-TFCI							E-TFCI																	OPTIONAL,
	iE-Extensions						ProtocolExtensionContainer { { Additional-EDCH-FDD-Information-ExtIEs} } OPTIONAL,
	...
}

Additional-EDCH-FDD-Information-ExtIEs	NBAP-PROTOCOL-EXTENSION ::= {
	...
}

Additional-EDCH-MAC-d-Flows-Specific-Info-List ::= SEQUENCE (SIZE (1..maxNrOfEDCHMACdFlows)) OF Additional-EDCH-MAC-d-Flows-Specific-Info

Additional-EDCH-MAC-d-Flows-Specific-Info ::= SEQUENCE {
	e-DCH-MACdFlow-ID								E-DCH-MACdFlow-ID,
	bindingID										BindingID																	OPTIONAL,
	transportLayerAddress							TransportLayerAddress														OPTIONAL,
	iE-Extensions									ProtocolExtensionContainer { { Additional-EDCH-MAC-d-Flows-Specific-Info-ExtIEs} }				OPTIONAL,
	...
}

Additional-EDCH-MAC-d-Flows-Specific-Info-ExtIEs	NBAP-PROTOCOL-EXTENSION ::= {
	...
}

Additional-EDCH-Cell-Information-Response-List	::= SEQUENCE (SIZE (1..maxNrOfEDCH-1)) OF Additional-EDCH-FDD-Information-Response-ItemIEs

Additional-EDCH-FDD-Information-Response-ItemIEs	::=SEQUENCE{
	eDCH-Additional-RL-Specific-Information-Response						EDCH-Additional-RL-Specific-Information-Response-List	OPTIONAL,
	additional-EDCH-MAC-d-Flow-Specific-Information-Response				Additional-EDCH-MAC-d-Flow-Specific-Information-Response-List		OPTIONAL,
	hARQ-Process-Allocation-Scheduled-2ms-EDCH								HARQ-Process-Allocation-2ms-EDCH					OPTIONAL,
	iE-Extensions					ProtocolExtensionContainer { { Additional-EDCH-FDD-Information-Response-ItemIEs-ExtIEs} } OPTIONAL,
	...
}

Additional-EDCH-FDD-Information-Response-ItemIEs-ExtIEs	NBAP-PROTOCOL-EXTENSION ::= {
	...
}

EDCH-Additional-RL-Specific-Information-Response-List	::= SEQUENCE (SIZE (1..maxNrOfEDCHRLs)) OF EDCH-Additional-RL-Specific-Information-Response-ItemIEs

EDCH-Additional-RL-Specific-Information-Response-ItemIEs	::=SEQUENCE{
	eDCH-Additional-RL-ID							RL-ID,
	received-total-wide-band-power					Received-total-wide-band-power-Value,
	dL-PowerBalancing-ActivationIndicator			DL-PowerBalancing-ActivationIndicator	OPTIONAL,
	rL-Set-ID										RL-Set-ID,
	e-DCH-RL-Set-ID									RL-Set-ID,
	e-DCH-FDD-DL-Control-Channel-Information		E-DCH-FDD-DL-Control-Channel-Information,
	iE-Extensions					ProtocolExtensionContainer { { EDCH-Additional-RL-Specific-Information-Response-ItemIEs-ExtIEs} } OPTIONAL,
	...
}

EDCH-Additional-RL-Specific-Information-Response-ItemIEs-ExtIEs	NBAP-PROTOCOL-EXTENSION ::= {
	...
}

Additional-EDCH-Cell-Information-Response-RLReconf-List::= SEQUENCE (SIZE (1..maxNrOfEDCH-1)) OF Additional-EDCH-FDD-Information-Response-RLReconf-Items

Additional-EDCH-FDD-Information-Response-RLReconf-Items::=SEQUENCE{
	additional-EDCH-FDD-Information-Response-ItemIEs				Additional-EDCH-FDD-Information-Response-ItemIEs					OPTIONAL,
	additional-Modififed-EDCH-FDD-Information-Response-ItemIEs		Additional-Modififed-EDCH-FDD-Information-Response-ItemIEs		OPTIONAL,
	iE-Extensions					ProtocolExtensionContainer { { Additional-EDCH-FDD-Information-Response-RLReconf-Items-ExtIEs} } OPTIONAL,
	...
}

Additional-EDCH-FDD-Information-Response-RLReconf-Items-ExtIEs	NBAP-PROTOCOL-EXTENSION ::= {
	...
}

Additional-Modififed-EDCH-FDD-Information-Response-ItemIEs	::=SEQUENCE{
	eDCH-Additional-Modified-RL-Specific-Information-Response		EDCH-Additional-Modified-RL-Specific-Information-Response-List		OPTIONAL,
	additional-EDCH-MAC-d-Flow-Specific-Information-Response		Additional-EDCH-MAC-d-Flow-Specific-Information-Response-List		OPTIONAL,
	hARQ-Process-Allocation-Scheduled-2ms-EDCH						HARQ-Process-Allocation-2ms-EDCH							OPTIONAL,
	iE-Extensions					ProtocolExtensionContainer { { Additional-Modififed-EDCH-FDD-Information-Response-ItemIEs-ExtIEs} } OPTIONAL,
	...
}

Additional-Modififed-EDCH-FDD-Information-Response-ItemIEs-ExtIEs	NBAP-PROTOCOL-EXTENSION ::= {
	...
}

EDCH-Additional-Modified-RL-Specific-Information-Response-List	::= SEQUENCE (SIZE (1.. maxNrOfEDCHRLs)) OF EDCH-Additional-Modified-RL-Specific-Information-Response-List-Items

EDCH-Additional-Modified-RL-Specific-Information-Response-List-Items	::=SEQUENCE{
	eDCH-Additional-RL-ID							RL-ID,
	dL-PowerBalancing-UpdatedIndicator				DL-PowerBalancing-UpdatedIndicator			OPTIONAL,
	e-DCH-FDD-DL-Control-Channel-Information		E-DCH-FDD-DL-Control-Channel-Information	OPTIONAL,
	iE-Extensions					ProtocolExtensionContainer { { EDCH-Additional-Modified-RL-Specific-Information-Response-List-Items-ExtIEs} } OPTIONAL,
	...
}

EDCH-Additional-Modified-RL-Specific-Information-Response-List-Items-ExtIEs	NBAP-PROTOCOL-EXTENSION ::= {
	...
}

Additional-EDCH-MAC-d-Flow-Specific-Information-Response-List::= SEQUENCE (SIZE (1..maxNrOfEDCHMACdFlows)) OF Additional-EDCH-MAC-d-Flows-Specific-Info-Response

Additional-EDCH-MAC-d-Flows-Specific-Info-Response ::= SEQUENCE {
	e-DCH-MACdFlow-ID								E-DCH-MACdFlow-ID,
	bindingID										BindingID																	OPTIONAL,
	transportLayerAddress							TransportLayerAddress														OPTIONAL,
	iE-Extensions									ProtocolExtensionContainer { { Additional-EDCH-MAC-d-Flows-Specific-Info-Response-ExtIEs} }				OPTIONAL,
	...
}

Additional-EDCH-MAC-d-Flows-Specific-Info-Response-ExtIEs	NBAP-PROTOCOL-EXTENSION ::= {
	...
}

Additional-EDCH-Cell-Information-Response-RL-Add-List	::= SEQUENCE (SIZE (1..maxNrOfEDCH-1)) OF Additional-EDCH-Cell-Information-Response-RL-Add-ItemIEs

Additional-EDCH-Cell-Information-Response-RL-Add-ItemIEs	::=SEQUENCE{
	additional-EDCH-FDD-Information-Response					Additional-EDCH-FDD-Information-Response-ItemIEs 	OPTIONAL,
	additional-EDCH-Serving-Cell-Change-Information-Response	E-DCH-Serving-Cell-Change-Info-Response 				OPTIONAL,
	iE-Extensions					ProtocolExtensionContainer { { Additional-EDCH-Cell-Information-Response-RL-Add-ItemIEs-ExtIEs} } OPTIONAL,
	...
}

Additional-EDCH-Cell-Information-Response-RL-Add-ItemIEs-ExtIEs	NBAP-PROTOCOL-EXTENSION ::= {
	...
}

Additional-EDCH-Cell-Information-ConfigurationChange-List	::= SEQUENCE (SIZE (1..maxNrOfEDCH-1)) OF Additional-EDCH-ConfigurationChange-Info-ItemIEs

Additional-EDCH-ConfigurationChange-Info-ItemIEs	::=SEQUENCE{
	additional-EDCH-UL-DPCH-Information-Modify							Additional-EDCH-UL-DPCH-Information-Modify		OPTIONAL,
	additional-EDCH-RL-Specific-Information-To-Add						Additional-EDCH-RL-Specific-Information-To-Add-ItemIEs 	OPTIONAL,
	additional-EDCH-RL-Specific-Information-To-Modify					Additional-EDCH-RL-Specific-Information-To-Modify-List 	OPTIONAL,
	additional-EDCH-FDD-Information-To-Modify							Additional-EDCH-FDD-Information		OPTIONAL,
	additional-EDCH-F-DPCH-Information-Modify							Additional-EDCH-F-DPCH-Information		OPTIONAL,
	multicell-EDCH-Information											Multicell-EDCH-Information		OPTIONAL,
	iE-Extensions					ProtocolExtensionContainer { { Additional-EDCH-ConfigurationChange-Info-ItemIEs-ExtIEs} } OPTIONAL,
	...
}

Additional-EDCH-ConfigurationChange-Info-ItemIEs-ExtIEs	NBAP-PROTOCOL-EXTENSION ::= {
	...
}

Additional-EDCH-UL-DPCH-Information-Modify		::=SEQUENCE{
	ul-ScramblingCode						UL-ScramblingCode 	OPTIONAL,
	ul-SIR-Target							UL-SIR 				OPTIONAL,
	iE-Extensions							ProtocolExtensionContainer { { Additional-EDCH-UL-DPCH-Information-Modify-ExtIEs} } OPTIONAL,
	...
}

Additional-EDCH-UL-DPCH-Information-Modify-ExtIEs	NBAP-PROTOCOL-EXTENSION ::= {
	...
}

Additional-EDCH-Cell-Information-Removal-List	::= SEQUENCE (SIZE (1..maxNrOfEDCH-1)) OF Additional-EDCH-Cell-Information-Removal-Info-ItemIEs

Additional-EDCH-Cell-Information-Removal-Info-ItemIEs	::=SEQUENCE{
	rL-on-Secondary-UL-Frequency							RL-on-Secondary-UL-Frequency,
	iE-Extensions					ProtocolExtensionContainer { { Additional-EDCH-Cell-Information-Removal-Info-ItemIEs-ExtIEs} } OPTIONAL,
	...
}

Additional-EDCH-Cell-Information-Removal-Info-ItemIEs-ExtIEs	NBAP-PROTOCOL-EXTENSION ::= {
	...
}

RL-on-Secondary-UL-Frequency ::= ENUMERATED {
	remove,
	...
}

Additional-EDCH-FDD-Update-Information	::=SEQUENCE{
	hARQ-Process-Allocation-Scheduled-2ms-EDCH						HARQ-Process-Allocation-2ms-EDCH								OPTIONAL,
	additional-EDCH-DL-Control-Channel-Change-Information			Additional-EDCH-DL-Control-Channel-Change-Information-List					OPTIONAL,
	iE-Extensions					ProtocolExtensionContainer { { Additional-EDCH-FDD-Update-Information-ExtIEs} } OPTIONAL,
	...
}

Additional-EDCH-FDD-Update-Information-ExtIEs	NBAP-PROTOCOL-EXTENSION ::= {
	...
}


Additional-EDCH-DL-Control-Channel-Change-Information-List	::= SEQUENCE (SIZE (1..maxNrOfEDCHRLs)) OF Additional-EDCH-DL-Control-Channel-Change-Info-ItemIEs

Additional-EDCH-DL-Control-Channel-Change-Info-ItemIEs	::=SEQUENCE{
	eDCH-Additional-RL-ID				RL-ID,
	iE-Extensions						ProtocolExtensionContainer { { Additional-EDCH-DL-Control-Channel-Change-Info-ItemIEs-ExtIEs} } OPTIONAL,
	...
}

Additional-EDCH-DL-Control-Channel-Change-Info-ItemIEs-ExtIEs	NBAP-PROTOCOL-EXTENSION ::= {
	...
}

AdditionalMeasurementValueList::= SEQUENCE (SIZE (1..maxFrequencyinCell-1)) OF AdditionalMeasurementValue

AdditionalMeasurementValue ::= SEQUENCE {
	uARFCN									UARFCN,
	timeSlotMeasurementValueListLCR			TimeSlotMeasurementValueListLCR,
	iE-Extensions							ProtocolExtensionContainer { {AdditionalMeasurementValueList-ExtIEs} } OPTIONAL,
	...
}

AdditionalMeasurementValueList-ExtIEs NBAP-PROTOCOL-EXTENSION ::= {
	...
}

AdditionalTimeSlotListLCR::= SEQUENCE (SIZE (0..maxFrequencyinCell-1)) OF AdditionalTimeSlotLCR

AdditionalTimeSlotLCR ::= SEQUENCE {
	uARFCN								UARFCN,
	timeslot-InitiatedListLCR					TimeSlot-InitiatedListLCR	 OPTIONAL,
	iE-Extensions								ProtocolExtensionContainer { {AdditionalTimeSlotLCR-ExtIEs} } OPTIONAL,
	...
}

AdditionalTimeSlotLCR-ExtIEs NBAP-PROTOCOL-EXTENSION ::= {
	...
}

AddorDeleteIndicator ::= ENUMERATED {
	add,
	delete
}

Active-Pattern-Sequence-Information ::= SEQUENCE {
	cMConfigurationChangeCFN								CFN,
	transmission-Gap-Pattern-Sequence-Status	Transmission-Gap-Pattern-Sequence-Status-List	OPTIONAL,
	iE-Extensions								ProtocolExtensionContainer { {Active-Pattern-Sequence-Information-ExtIEs} } OPTIONAL,
	...
}

Active-Pattern-Sequence-Information-ExtIEs NBAP-PROTOCOL-EXTENSION ::= {
	...
}

Transmission-Gap-Pattern-Sequence-Status-List ::= SEQUENCE (SIZE (0..maxTGPS)) OF
	SEQUENCE {
		tGPSID			TGPSID,
		tGPRC			TGPRC,
		tGCFN			CFN,
		iE-Extensions		ProtocolExtensionContainer { { Transmission-Gap-Pattern-Sequence-Status-List-ExtIEs } } OPTIONAL,
		...
}

Transmission-Gap-Pattern-Sequence-Status-List-ExtIEs NBAP-PROTOCOL-EXTENSION ::= {
	...
}

AICH-Power ::= INTEGER (-22..5)
-- Offset in dB.

AICH-TransmissionTiming ::= ENUMERATED {
	v0,
	v1
}

AllocationRetentionPriority ::= SEQUENCE {
	priorityLevel				PriorityLevel,
	pre-emptionCapability		Pre-emptionCapability,
	pre-emptionVulnerability	Pre-emptionVulnerability,
	iE-Extensions				ProtocolExtensionContainer { {AllocationRetentionPriority-ExtIEs} } OPTIONAL,
	...
}

AllocationRetentionPriority-ExtIEs NBAP-PROTOCOL-EXTENSION ::= {
	...
}

AlternativeFormatReportingIndicator ::= ENUMERATED {
alternativeFormatAllowed,...
}

Angle-Of-Arrival-Value-LCR ::= SEQUENCE {
	aOA-LCR						AOA-LCR,
	aOA-LCR-Accuracy-Class		AOA-LCR-Accuracy-Class,
	iE-Extensions				ProtocolExtensionContainer { {Angle-Of-Arrival-Value-LCR-ExtIEs} } OPTIONAL,
...
}

Angle-Of-Arrival-Value-LCR-ExtIEs NBAP-PROTOCOL-EXTENSION ::= {
	...
}

AOA-LCR ::= INTEGER (0..719)
-- Angle Of Arrival for 1.28Mcps TDD

AOA-LCR-Accuracy-Class	::= ENUMERATED {a,b,c,d,e,f,g,h,...}

AvailabilityStatus ::= ENUMERATED {
	empty,
	in-test,
	failed,
	power-off,
	off-line,
	off-duty,
	dependency,
	degraded,
	not-installed,
	log-full,
	...
}

-- ==========================================
--	B
-- ==========================================

BCCH-Specific-HSDSCH-RNTI-Information::= SEQUENCE {
	bCCH-Specific-HSDSCH-RNTI						HSDSCH-RNTI,
	hSSCCH-Power									DL-Power,
	hSPDSCH-Power									DL-Power,
	iE-Extensions									ProtocolExtensionContainer { { BCCH-Specific-HSDSCH-RNTI-Information-ExtIEs } }		OPTIONAL,
	...
}

BCCH-Specific-HSDSCH-RNTI-Information-ExtIEs NBAP-PROTOCOL-EXTENSION ::= {
	...
}


BCCH-Specific-HSDSCH-RNTI-InformationLCR::= SEQUENCE {
	bCCH-Specific-HSDSCH-RNTI						HSDSCH-RNTI,
	hSSCCH-Power									DL-Power,
	hSPDSCH-Power									DL-Power,
	iE-Extensions									ProtocolExtensionContainer { { BCCH-Specific-HSDSCH-RNTI-InformationLCR-ExtIEs } }		OPTIONAL,
	...
}

BCCH-Specific-HSDSCH-RNTI-InformationLCR-ExtIEs NBAP-PROTOCOL-EXTENSION ::= {
	...
}


BCCH-ModificationTime ::= INTEGER  (0..511)
-- Time = BCCH-ModificationTime * 8
-- Range 0 to 4088, step 8
-- All SFN values in which MIB may be mapped are allowed

Best-Cell-Portions-Value::= SEQUENCE (SIZE (1..maxNrOfCellPortionsPerCell)) OF Best-Cell-Portions-Item

Best-Cell-Portions-Item ::= SEQUENCE {
	cellPortionID				CellPortionID,
	sIRValue					SIR-Value,
	iE-Extensions				ProtocolExtensionContainer { { Best-Cell-Portions-Item-ExtIEs} }	OPTIONAL,
	...
}

Best-Cell-Portions-Item-ExtIEs NBAP-PROTOCOL-EXTENSION ::= {
	...
}

Best-Cell-Portions-ValueLCR::= SEQUENCE (SIZE (1..maxNrOfCellPortionsPerCellLCR)) OF Best-Cell-Portions-ItemLCR

Best-Cell-Portions-ItemLCR ::= SEQUENCE {
	cellPortionLCRID				CellPortionLCRID,
	rSCPValue						RSCP-Value,
	iE-Extensions				ProtocolExtensionContainer { { Best-Cell-Portions-ItemLCR-ExtIEs} }	OPTIONAL,
	...
}

Best-Cell-Portions-ItemLCR-ExtIEs NBAP-PROTOCOL-EXTENSION ::= {
	...
}

BindingID ::= OCTET STRING (SIZE (1..4, ...))
-- If the Binding ID includes a UDP port, the UDP port is included in octet 1 and 2.The first octet of
-- the UDP port field is included in the first octet of the Binding ID.

BetaCD ::= INTEGER (0..15)

BlockingPriorityIndicator ::= ENUMERATED {
	high,
	normal,
	low,
	...
}
-- High priority: Block resource immediately.
-- Normal priority: Block resource when idle or upon timer expiry.
-- Low priority: Block resource when idle.

SCTD-Indicator ::= ENUMERATED {
	active,
	inactive
}

BundlingModeIndicator ::= ENUMERATED {
	bundling,
	no-bundling
}

BroadcastCommonTransportBearerIndication ::= SEQUENCE {
	commonTransportChannelID			CommonTransportChannelID,
	cid									C-ID,
	iE-Extensions						ProtocolExtensionContainer  { { BroadcastCommonTransportBearerIndication-ExtIEs} }		OPTIONAL,
	...
}

BroadcastCommonTransportBearerIndication-ExtIEs NBAP-PROTOCOL-EXTENSION ::= {
	...
}

BroadcastReference ::= BIT STRING (SIZE (24))

-- ==========================================
--	C
-- ==========================================

Cause ::= CHOICE {
	radioNetwork			CauseRadioNetwork,
	transport			CauseTransport,
	protocol				CauseProtocol,
	misc					CauseMisc,
	...
}

CauseMisc ::= ENUMERATED {
	control-processing-overload,
	hardware-failure,
	oam-intervention,
	not-enough-user-plane-processing-resources,
	unspecified,
	...
}

CauseProtocol ::= ENUMERATED {
	transfer-syntax-error,
	abstract-syntax-error-reject,
	abstract-syntax-error-ignore-and-notify,
	message-not-compatible-with-receiver-state,
	semantic-error,
	unspecified,
	abstract-syntax-error-falsely-constructed-message,
	...
}

CauseRadioNetwork ::= ENUMERATED {
	unknown-C-ID,
	cell-not-available,
	power-level-not-supported,
	dl-radio-resources-not-available,
	ul-radio-resources-not-available,
	rl-already-ActivatedOrAllocated,
	nodeB-Resources-unavailable,
	measurement-not-supported-for-the-object,
	combining-resources-not-available,
	requested-configuration-not-supported,
	synchronisation-failure,
	priority-transport-channel-established,
	sIB-Origination-in-Node-B-not-Supported,
	requested-tx-diversity-mode-not-supported,
	unspecified,
	bCCH-scheduling-error,
	measurement-temporarily-not-available,
	invalid-CM-settings,
	reconfiguration-CFN-not-elapsed,
	number-of-DL-codes-not-supported,
	s-cpich-not-supported,
	combining-not-supported,
	ul-sf-not-supported,
	dl-SF-not-supported,
	common-transport-channel-type-not-supported,
	dedicated-transport-channel-type-not-supported,
	downlink-shared-channel-type-not-supported,
	uplink-shared-channel-type-not-supported,
	cm-not-supported,
	tx-diversity-no-longer-supported,
	unknown-Local-Cell-ID,
	...,
    number-of-UL-codes-not-supported,
    information-temporarily-not-available,
    information-provision-not-supported-for-the-object,
	cell-synchronisation-not-supported,
	cell-synchronisation-adjustment-not-supported,
	dpc-mode-change-not-supported,
	iPDL-already-activated,
	iPDL-not-supported,
	iPDL-parameters-not-available,
	frequency-acquisition-not-supported,
	power-balancing-status-not-compatible,
	requested-typeofbearer-re-arrangement-not-supported,
	signalling-Bearer-Re-arrangement-not-supported,
	bearer-Re-arrangement-needed,
	delayed-activation-not-supported,
	rl-timing-adjustment-not-supported,
	mich-not-supported,
	f-DPCH-not-supported,
	modification-period-not-available,
	pLCCH-not-supported,
	continuous-packet-connectivity-DTX-DRX-operation-not-available,
	continuous-packet-connectivity-UE-DTX-Cycle-not-available,
	mIMO-not-available,
	e-DCH-MACdPDU-SizeFormat-not-available,
	multi-Cell-operation-not-available,
	semi-Persistent-scheduling-not-supported,
	continuous-Packet-Connectivity-DRX-not-supported,
	continuous-Packet-Connectivity-DRX-not-available,
	sixtyfourQAM-DL-and-MIMO-Combined-not-available,
	s-cpich-power-offset-not-available,
	tx-diversity-for-mimo-on-DL-control-channels-not-available,
	single-Stream-MIMO-not-available,
	multi-Cell-operation-with-MIMO-not-available,
	multi-Cell-operation-with-Single-Stream-MIMO-not-available,
	cellSpecificTxDiversityHandlingForMultiCellOperationNotAvailable,
	multi-Cell-EDCH-operation-not-available


}

CauseTransport ::= ENUMERATED {
	transport-resource-unavailable,
	unspecified,
	...
}


CCTrCH-ID ::= INTEGER (0..15)

Cell-Capability-Container ::= BIT STRING (SIZE (128))
-- First bit: Cell Specific Tx Diversity Handling For Multi Cell Operation Capability
-- Second bit: Multi Cell and MIMO Capability
-- Third bit: Multi Cell and Single Stream MIMO Capability
-- Fourth bit: Multi Cell E-DCH Capability
-- Fifth bit: Separate Iub Transport Bearer Capability
-- Sixth bit: E-DCH UL Flow Multiplexing Capability
-- Note that undefined bits are considered as a spare bit and spare bits shall be set to 0 by the transmitter and shall be ignored by the receiver.

Cell-ERNTI-Status-Information		::= SEQUENCE (SIZE (1..maxCellinNodeB)) OF Cell-ERNTI-Status-Information-Item

Cell-ERNTI-Status-Information-Item  ::= SEQUENCE {
	c-ID											C-ID,
	vacant-ERNTI									Vacant-ERNTI,
	...
}

Vacant-ERNTI 		::= SEQUENCE (SIZE (1..maxERNTItoRelease)) OF E-RNTI


CellParameterID ::= INTEGER (0..127,...)

CellPortionID	::= INTEGER (0..maxNrOfCellPortionsPerCell-1,...)

CellPortionLCRID	::= INTEGER (0..maxNrOfCellPortionsPerCellLCR-1,...)

CellPortion-CapabilityLCR ::= ENUMERATED {
	cell-portion-capable,
	cell-portion-non-capable
}

CellSyncBurstCode ::= INTEGER(0..7, ...)

CellSyncBurstCodeShift ::= INTEGER(0..7)

CellSyncBurstRepetitionPeriod ::= INTEGER (0..4095)

CellSyncBurstSIR ::= INTEGER (0..31)

CellSyncBurstTiming ::= CHOICE {
	initialPhase			INTEGER (0..1048575,...),
	steadyStatePhase		INTEGER (0..255,...)
}

CellSyncBurstTimingLCR ::= CHOICE {
	initialPhase			INTEGER (0..524287,...),
	steadyStatePhase		INTEGER (0..127,...)
}

CellSyncBurstTimingThreshold ::= INTEGER(0..254)

CFN ::= INTEGER (0..255)

ChipOffset ::= INTEGER (0..38399)
-- Unit Chip

C-ID ::= INTEGER (0..65535)

Closedlooptimingadjustmentmode	::= ENUMERATED {
	adj-1-slot,
	adj-2-slot,
	...
}

CodeRate ::= INTEGER (0..63)

CodeRate-short ::= INTEGER (0..10)


CommonChannelsCapacityConsumptionLaw ::= SEQUENCE (SIZE(1..maxNrOfSF)) OF
	SEQUENCE {
		dl-Cost		INTEGER (0..65535),
		ul-Cost		INTEGER (0..65535),
		iE-Extensions		ProtocolExtensionContainer { { CommonChannelsCapacityConsumptionLaw-ExtIEs } }		OPTIONAL,
		...
}

CommonChannelsCapacityConsumptionLaw-ExtIEs NBAP-PROTOCOL-EXTENSION ::= {
	...
}


Common-EDCH-Capability ::= ENUMERATED {
	common-EDCH-capable,
	common-EDCH-non-capable
}

Common-E-DCH-HSDPCCH-Capability ::= ENUMERATED {
	hSDPCCH-non-capable,
	aCK-NACK-capable,
	aCK-NACK-CQI-capable
}

Common-EDCH-System-InformationFDD ::= SEQUENCE {
	common-E-DCH-UL-DPCH-Information				Common-E-DCH-UL-DPCH-InfoItem								OPTIONAL,
	common-E-DCH-EDPCH-Information					Common-E-DCH-EDPCH-InfoItem									OPTIONAL,
	common-E-DCH-Information						Common-E-DCH-InfoItem										OPTIONAL,
	common-E-DCH-HSDPCCH-Information				Common-E-DCH-HSDPCCH-InfoItem							OPTIONAL,
	common-E-DCH-Preamble-Control-Information		Common-E-DCH-Preamble-Control-InfoItem						OPTIONAL,
	common-E-DCH-FDPCH-Information					Common-E-DCH-FDPCH-InfoItem									OPTIONAL,
	common-E-DCH-E-AGCH-ChannelisationCodeNumber	FDD-DL-ChannelisationCodeNumber								OPTIONAL,
	common-E-DCH-Resource-Combination-Information	Common-E-DCH-Resource-Combination-InfoList					OPTIONAL,
	ul-common-E-DCH-MACflow-Specific-Information	Ul-common-E-DCH-MACflow-Specific-InfoList					OPTIONAL,
	iE-Extensions									ProtocolExtensionContainer { { Common-EDCH-System-InformationFDD-ExtIEs } }		OPTIONAL,
	...
}

Common-EDCH-System-InformationFDD-ExtIEs NBAP-PROTOCOL-EXTENSION ::= {
	{ ID id-E-RNTI-List-Request 	CRITICALITY ignore	 EXTENSION NULL 	PRESENCE optional},
	...
}


Common-E-DCH-UL-DPCH-InfoItem ::= SEQUENCE {

	uL-SIR-Target						UL-SIR,
	dPC-Mode							DPC-Mode					OPTIONAL,
	iE-Extensions						ProtocolExtensionContainer { { Common-E-DCH-UL-DPCH-InfoItem-ExtIEs} }					OPTIONAL,
	...
}

Common-E-DCH-UL-DPCH-InfoItem-ExtIEs NBAP-PROTOCOL-EXTENSION ::= {
	...
}

Common-E-DCH-EDPCH-InfoItem	 ::= SEQUENCE {
	maxSet-E-DPDCHs								Max-Set-E-DPDCHs,
	ul-PunctureLimit							PunctureLimit,
	e-TFCS-Information							E-TFCS-Information,
	e-TTI										E-TTI,
	e-DPCCH-PO									E-DPCCH-PO,
	e-RGCH-2-IndexStepThreshold					E-RGCH-2-IndexStepThreshold						OPTIONAL,
	e-RGCH-3-IndexStepThreshold					E-RGCH-3-IndexStepThreshold						OPTIONAL,
	hARQ-Info-for-E-DCH							HARQ-Info-for-E-DCH,
	iE-Extensions								ProtocolExtensionContainer { { Common-E-DCH-EDPCH-InfoItem-ExtIEs} }					OPTIONAL,
	...
}

Common-E-DCH-EDPCH-InfoItem-ExtIEs NBAP-PROTOCOL-EXTENSION ::= {
	...
}

Common-E-DCH-InfoItem	 ::= SEQUENCE {
	e-DCH-Reference-Power-Offset				E-DCH-Reference-Power-Offset					OPTIONAL,
	e-DCH-PowerOffset-for-SchedulingInfo		E-DCH-PowerOffset-for-SchedulingInfo			OPTIONAL,
	max-EDCH-Resource-Allocation-for-CCCH		Max-EDCH-Resource-Allocation-for-CCCH,
	max-Period-for-Collistion-Resolution		Max-Period-for-Collistion-Resolution,
	max-TB-Sizes									Max-TB-Sizes										OPTIONAL,
	common-E-DCH-ImplicitRelease-Indicator		BOOLEAN,
	iE-Extensions								ProtocolExtensionContainer { { Common-E-DCH-InfoItem-ExtIEs} }					OPTIONAL,
	...
}

Common-E-DCH-InfoItem-ExtIEs NBAP-PROTOCOL-EXTENSION ::= {
	...
}

Common-E-DCH-HSDPCCH-InfoItem	 ::= SEQUENCE {
	ackNackRepetitionFactor						AckNack-RepetitionFactor,

	ackPowerOffset								Ack-Power-Offset,
	nackPowerOffset								Nack-Power-Offset,

	common-E-DCH-CQI-Info						Common-E-DCH-CQI-Info						OPTIONAL,
	iE-Extensions								ProtocolExtensionContainer { { Common-E-DCH-HSDPCCH-InfoItem-ExtIEs} }					OPTIONAL,
	...
}

Common-E-DCH-HSDPCCH-InfoItem-ExtIEs NBAP-PROTOCOL-EXTENSION ::= {
	...
}


Common-E-DCH-CQI-Info	 ::= SEQUENCE {
	cqiFeedback-CycleK							CQI-Feedback-Cycle,
	cqiRepetitionFactor							CQI-RepetitionFactor						OPTIONAL,
	-- This IE shall be present if the CQI Feedback Cycle k is greater than 0
	cqiPowerOffset								CQI-Power-Offset,
	measurement-Power-Offset					Measurement-Power-Offset,
	iE-Extensions								ProtocolExtensionContainer { { Common-E-DCH-CQI-Info-ExtIEs} }					OPTIONAL,
	...
}

Common-E-DCH-CQI-Info-ExtIEs NBAP-PROTOCOL-EXTENSION ::= {
	...
}

Common-E-DCH-Preamble-Control-InfoItem	 ::= SEQUENCE {
	commonPhysicalChannelID						CommonPhysicalChannelID,
	common-E-DCH-PreambleSignatures				PreambleSignatures,
	scramblingCodeNumber						ScramblingCodeNumber,
	preambleThreshold							PreambleThreshold,
	e-AI-Indicator								E-AI-Indicator						OPTIONAL,
	common-E-DCH-AICH-Information				Common-E-DCH-AICH-Information						OPTIONAL,
	iE-Extensions								ProtocolExtensionContainer { { Common-E-DCH-Preamble-Control-InfoItem-ExtIEs} }					OPTIONAL,
	...
}

Common-E-DCH-Preamble-Control-InfoItem-ExtIEs NBAP-PROTOCOL-EXTENSION ::= {
	...
}

Common-E-DCH-AICH-Information	 ::= SEQUENCE {
	commonPhysicalChannelID						CommonPhysicalChannelID,
	aICH-TransmissionTiming						AICH-TransmissionTiming,
	fdd-dl-ChannelisationCodeNumber				FDD-DL-ChannelisationCodeNumber,
	aICH-Power									AICH-Power,
	sTTD-Indicator								STTD-Indicator,
	iE-Extensions								ProtocolExtensionContainer  { { Common-E-DCH-AICH-Information-ExtIEs} }		OPTIONAL,
	...
}

Common-E-DCH-AICH-Information-ExtIEs NBAP-PROTOCOL-EXTENSION ::= {
	...
}




Common-E-DCH-FDPCH-InfoItem		 ::= SEQUENCE {
	f-DPCH-SlotFormat							F-DPCH-SlotFormat,
	fdd-TPC-DownlinkStepSize					FDD-TPC-DownlinkStepSize,
	iE-Extensions								ProtocolExtensionContainer { { Common-E-DCH-FDPCH-InfoItem-ExtIEs} }					OPTIONAL,
	...
}

Common-E-DCH-FDPCH-InfoItem-ExtIEs NBAP-PROTOCOL-EXTENSION ::= {
	{ ID id-Initial-DL-Transmission-Power	CRITICALITY ignore		EXTENSION DL-Power		PRESENCE optional }|
	{ ID id-Maximum-DL-Power				CRITICALITY ignore		EXTENSION DL-Power		PRESENCE optional }|
	{ ID id-Minimum-DL-Power				CRITICALITY ignore		EXTENSION DL-Power		PRESENCE optional },
	...
}

Common-E-DCH-Resource-Combination-InfoList::= SEQUENCE (SIZE (1.. maxNrOfCommonEDCH)) OF Common-E-DCH-Resource-Combination-InfoList-Item

Common-E-DCH-Resource-Combination-InfoList-Item		 ::= SEQUENCE {
	soffset										Soffset,
	f-DPCH-DL-Code-Number						FDD-DL-ChannelisationCodeNumber,
	ul-DPCH-ScramblingCode						UL-ScramblingCode,
	e-RGCH-E-HICH-Channelisation-Code			FDD-DL-ChannelisationCodeNumber,
	e-RGCH-Signature-Sequence					E-RGCH-Signature-Sequence													OPTIONAL,
	e-HICH-Signature-Sequence					E-HICH-Signature-Sequence,
	iE-Extensions								ProtocolExtensionContainer { { Common-E-DCH-Resource-Combination-InfoList-Item-ExtIEs} }					OPTIONAL,
	...
}

Common-E-DCH-Resource-Combination-InfoList-Item-ExtIEs NBAP-PROTOCOL-EXTENSION ::= {
	...
}

Ul-common-E-DCH-MACflow-Specific-InfoList		::= SEQUENCE (SIZE (1..maxNrOfCommonMACFlows)) OF Ul-common-E-DCH-MACflow-Specific-InfoList-Item

Ul-common-E-DCH-MACflow-Specific-InfoList-Item		 ::= SEQUENCE {
	ul-Common-MACFlowID									Common-MACFlow-ID,
	transportBearerRequestIndicator						TransportBearerRequestIndicator,
	bindingID											BindingID										OPTIONAL,
	transportLayerAddress								TransportLayerAddress							OPTIONAL,
	tnlQos												TnlQos											OPTIONAL,
	payloadCRC-PresenceIndicator						PayloadCRC-PresenceIndicator,
	bundlingModeIndicator								BundlingModeIndicator							OPTIONAL,
	common-E-DCH-MACdFlow-Specific-Information			Common-E-DCH-MACdFlow-Specific-InfoList,
	iE-Extensions										ProtocolExtensionContainer { { Ul-common-E-DCH-MACflow-Specific-InfoList-Item-ExtIEs} }					OPTIONAL,
	...
}

Ul-common-E-DCH-MACflow-Specific-InfoList-Item-ExtIEs NBAP-PROTOCOL-EXTENSION ::= {
	...
}

Common-E-DCH-MACdFlow-Specific-InfoList::= SEQUENCE (SIZE (1.. maxNrOfEDCHMACdFlows)) OF Common-E-DCH-MACdFlow-Specific-InfoList-Item

Common-E-DCH-MACdFlow-Specific-InfoList-Item		 ::= SEQUENCE {
	common-e-DCH-MACdFlow-ID						E-DCH-MACdFlow-ID,
	maximum-Number-of-Retransmissions-For-E-DCH		Maximum-Number-of-Retransmissions-For-E-DCH,
	eDCH-HARQ-PO-FDD								E-DCH-HARQ-PO-FDD,
	eDCH-MACdFlow-Multiplexing-List					E-DCH-MACdFlow-Multiplexing-List																	OPTIONAL,
	common-E-DCHLogicalChannelInformation			Common-E-DCH-LogicalChannel-InfoList,
	iE-Extensions									ProtocolExtensionContainer { { Common-E-DCH-MACdFlow-Specific-InfoList-Item-ExtIEs} }				OPTIONAL,
	...
}

Common-E-DCH-MACdFlow-Specific-InfoList-Item-ExtIEs NBAP-PROTOCOL-EXTENSION ::= {
	...
}

Common-E-DCH-LogicalChannel-InfoList::= SEQUENCE (SIZE (1.. maxNoOfLogicalChannels)) OF Common-E-DCH-LogicalChannel-InfoList-Item

Common-E-DCH-LogicalChannel-InfoList-Item	::= SEQUENCE {
	logicalChannelId				LogicalChannelID,
	maximumMACcPDU-SizeExtended		MAC-PDU-SizeExtended,
	iE-Extensions									ProtocolExtensionContainer { { Common-E-DCH-LogicalChannel-InfoList-Item-ExtIEs} }				OPTIONAL,
	...
}

Common-E-DCH-LogicalChannel-InfoList-Item-ExtIEs NBAP-PROTOCOL-EXTENSION ::= {
{ ID id-schedulingPriorityIndicator	CRITICALITY ignore		EXTENSION	SchedulingPriorityIndicator	PRESENCE optional},
	...
}


Common-EDCH-System-Information-ResponseFDD		 ::= SEQUENCE {
	ul-common-E-DCH-MACflow-Specific-InfoResponse			Ul-common-E-DCH-MACflow-Specific-InfoResponseList,
	serving-Grant-Value										E-Serving-Grant-Value,
	iE-Extensions											ProtocolExtensionContainer { { Common-EDCH-System-Information-ResponseFDD-ExtIEs} }					OPTIONAL,
	...
}

Common-EDCH-System-Information-ResponseFDD-ExtIEs NBAP-PROTOCOL-EXTENSION ::= {
{ ID id-E-RNTI-List	CRITICALITY ignore		EXTENSION	E-RNTI-List	PRESENCE optional},
	...
}

E-RNTI-List 		::= SEQUENCE (SIZE (1..maxofERNTI)) OF E-RNTI

Ul-common-E-DCH-MACflow-Specific-InfoResponseList		::= SEQUENCE (SIZE (1..maxNrOfCommonMACFlows)) OF Ul-common-E-DCH-MACflow-Specific-InfoResponseList-Item

Ul-common-E-DCH-MACflow-Specific-InfoResponseList-Item		 ::= SEQUENCE {
	ul-Common-MACFlowID									Common-MACFlow-ID,
	bindingID											BindingID										OPTIONAL,
	transportLayerAddress								TransportLayerAddress							OPTIONAL,
	iE-Extensions										ProtocolExtensionContainer { { Ul-common-E-DCH-MACflow-Specific-InfoResponseList-Item-ExtIEs} }					OPTIONAL,
	...
}

Ul-common-E-DCH-MACflow-Specific-InfoResponseList-Item-ExtIEs NBAP-PROTOCOL-EXTENSION ::= {
	...
}

Common-MACFlows-to-DeleteFDD ::= SEQUENCE (SIZE (1.. maxNrOfCommonMACFlows)) OF Common-MACFlows-to-DeleteFDD-Item

Common-MACFlows-to-DeleteFDD-Item ::= SEQUENCE {
	common-MACFlow-ID								Common-MACFlow-ID,
	iE-Extensions									ProtocolExtensionContainer { { Common-MACFlows-to-DeleteFDD-Item-ExtIEs} }					OPTIONAL,
	...
}

Common-MACFlows-to-DeleteFDD-Item-ExtIEs NBAP-PROTOCOL-EXTENSION ::= {
	...
}

Common-MACFlow-ID ::= INTEGER (0..maxNrOfCommonMACFlows-1)

CommonMACFlow-Specific-InfoList ::= SEQUENCE (SIZE (1.. maxNrOfCommonMACFlows)) OF CommonMACFlow-Specific-InfoItem

CommonMACFlow-Specific-InfoItem ::= SEQUENCE {
	common-MACFlow-Id								Common-MACFlow-ID,
	bindingID										BindingID									OPTIONAL,
	transportLayerAddress							TransportLayerAddress						OPTIONAL,
	tnl-qos											TnlQos										OPTIONAL,
	common-MACFlow-PriorityQueue-Information		Common-MACFlow-PriorityQueue-Information	OPTIONAL,
	iE-Extensions									ProtocolExtensionContainer { { CommonMACFlow-Specific-InfoItem-ExtIEs } }		OPTIONAL,
	...
}

CommonMACFlow-Specific-InfoItem-ExtIEs NBAP-PROTOCOL-EXTENSION ::= {
	{ ID id-TransportBearerRequestIndicator 	CRITICALITY ignore	 EXTENSION TransportBearerRequestIndicator 	PRESENCE optional},
	-- This IE should not be contained if the MAC flow is setup in procedure, and it should be contained if the MAC flow is modified in procedure.
	...
}


CommonMACFlow-Specific-InfoList-Response ::= SEQUENCE (SIZE (1..maxNrOfCommonMACFlows)) OF CommonMACFlow-Specific-InfoItem-Response

CommonMACFlow-Specific-InfoItem-Response ::= SEQUENCE {
	commonMACFlow-ID								Common-MACFlow-ID,
	bindingID										BindingID									OPTIONAL,
	transportLayerAddress							TransportLayerAddress						OPTIONAL,
	hSDSCH-Initial-Capacity-Allocation				HSDSCH-Initial-Capacity-Allocation			OPTIONAL,
	iE-Extensions									ProtocolExtensionContainer { { CommonMACFlow-Specific-InfoItem-Response-ExtIEs} }			OPTIONAL,
	...
}

CommonMACFlow-Specific-InfoItem-Response-ExtIEs NBAP-PROTOCOL-EXTENSION ::= {
	...
}

Common-MACFlow-PriorityQueue-Information  ::= SEQUENCE (SIZE (1..maxNrOfcommonMACQueues)) OF Common-MACFlow-PriorityQueue-Item

Common-MACFlow-PriorityQueue-Item  ::= SEQUENCE {
	priority-Queue-Information-for-Enhanced-FACH		Priority-Queue-Information-for-Enhanced-FACH-PCH,
		iE-Extensions									ProtocolExtensionContainer { { Common-MACFlow-PriorityQueue-Item-ExtIEs } }		OPTIONAL,
	...
}

Common-MACFlow-PriorityQueue-Item-ExtIEs NBAP-PROTOCOL-EXTENSION ::= {
	...
}




CommonMeasurementAccuracy ::= CHOICE {
	tUTRANGPSMeasurementAccuracyClass		TUTRANGPSAccuracyClass,
	...,
	tUTRANGANSSMeasurementAccuracyClass		TUTRANGANSSAccuracyClass
}

CommonMeasurementType ::= ENUMERATED  {
	received-total-wide-band-power,
	transmitted-carrier-power,
	acknowledged-prach-preambles,
	ul-timeslot-iscp,
	notUsed-1-acknowledged-PCPCH-access-preambles,
	notUsed-2-detected-PCPCH-access-preambles,
	...,
	uTRAN-GPS-Timing-of-Cell-Frames-for-UE-Positioning,
	sFN-SFN-Observed-Time-Difference,
	transmittedCarrierPowerOfAllCodesNotUsedForHSTransmission,
	hS-DSCH-Required-Power,
	hS-DSCH-Provided-Bit-Rate,
	received-total-wide-band-power-for-cellPortion,
	transmitted-carrier-power-for-cellPortion,
	transmittedCarrierPowerOfAllCodesNotUsedForHS-PDSCH-HS-SCCH-E-AGCH-E-RGCHOrE-HICHTransmission-for-cellPortion,
	upPTS-Interference,
	dLTransmissionBranchLoad,
	hS-DSCH-Required-Power-for-cell-portion,
	hS-DSCH-Provided-Bit-Rate-for-cell-portion,
	e-DCH-Provided-Bit-Rate,
	e-DCH-Non-serving-Relative-Grant-Down-Commands,
	received-Scheduled-EDCH-Power-Share,
	received-Scheduled-EDCH-Power-Share-for-cellPortion,
	uTRAN-GANSS-timing-of-cell-frames-for-UE-Positioning,
	eDCH-RACH-report,
	transmittedCarrierPowerOfAllCodesNotUsedForHS-PDSCH-HS-SCCH-E-AGCHOrE-HICHTransmission-for-cellPortion,
	ul-timeslot-iscp-for-cellPortion,
	upPTS-Interference-for-cellPortion,
	e-DCH-Provided-Bit-Rate-for-cellPortion

}

CommonMeasurementValue ::= CHOICE {
	transmitted-carrier-power							Transmitted-Carrier-Power-Value,
	received-total-wide-band-power						Received-total-wide-band-power-Value,
	acknowledged-prach-preambles						Acknowledged-PRACH-preambles-Value,
	uL-TimeslotISCP										UL-TimeslotISCP-Value,
	notUsed-1-acknowledged-PCPCH-access-preambles		NULL,
	notUsed-2-detected-PCPCH-access-preambles			NULL,
	...,
	extension-CommonMeasurementValue		Extension-CommonMeasurementValue
}

Extension-CommonMeasurementValue	::= ProtocolIE-Single-Container {{ Extension-CommonMeasurementValueIE }}

Extension-CommonMeasurementValueIE NBAP-PROTOCOL-IES ::= {
	{ ID id-TUTRANGPSMeasurementValueInformation			CRITICALITY ignore	TYPE TUTRANGPSMeasurementValueInformation		PRESENCE mandatory }|
	{ ID id-SFNSFNMeasurementValueInformation				CRITICALITY ignore	TYPE SFNSFNMeasurementValueInformation			PRESENCE mandatory }|
	{ ID id-TransmittedCarrierPowerOfAllCodesNotUsedForHSTransmission	CRITICALITY ignore	TYPE TransmittedCarrierPowerOfAllCodesNotUsedForHSTransmissionValue		PRESENCE mandatory }|
	{ ID id-HS-DSCHRequiredPowerValueInformation			CRITICALITY ignore	TYPE HS-DSCHRequiredPower							PRESENCE mandatory }|
	{ ID id-HS-DSCHProvidedBitRateValueInformation			CRITICALITY ignore	TYPE HS-DSCHProvidedBitRate						PRESENCE mandatory }|
	{ ID id-Transmitted-Carrier-Power-For-CellPortion-Value	CRITICALITY ignore	TYPE Transmitted-Carrier-Power-For-CellPortion-Value	PRESENCE mandatory }|
	{ ID id-Received-total-wide-band-power-For-CellPortion-Value	CRITICALITY ignore	TYPE Received-total-wide-band-power-For-CellPortion-Value	PRESENCE mandatory }|
	{ ID id-TransmittedCarrierPowerOfAllCodesNotUsedForHS-PDSCH-HS-SCCH-E-AGCH-E-RGCHOrE-HICHTransmissionCellPortionValue	CRITICALITY ignore	TYPE TransmittedCarrierPowerOfAllCodesNotUsedForHS-PDSCH-HS-SCCH-E-AGCH-E-RGCHOrE-HICHTransmissionCellPortionValue		PRESENCE mandatory }|
	{ ID id-UpPTSInterferenceValue									CRITICALITY ignore	TYPE UpPTSInterferenceValue									PRESENCE mandatory }|
	{ ID id-DLTransmissionBranchLoadValue							CRITICALITY ignore	TYPE DLTransmissionBranchLoadValue							PRESENCE mandatory }|
	{ ID id-HS-DSCHRequiredPowerValueInformation-For-CellPortion	CRITICALITY ignore	TYPE HS-DSCHRequiredPowerValueInformation-For-CellPortion	PRESENCE mandatory }|
	{ ID id-HS-DSCHProvidedBitRateValueInformation-For-CellPortion	CRITICALITY ignore	TYPE HS-DSCHProvidedBitRateValueInformation-For-CellPortion	PRESENCE mandatory }|
	{ ID id-E-DCHProvidedBitRateValueInformation					CRITICALITY ignore	TYPE E-DCHProvidedBitRate										PRESENCE mandatory }|
	{ ID id-E-DCH-Non-serving-Relative-Grant-Down-CommandsValue		CRITICALITY ignore	TYPE E-DCH-Non-serving-Relative-Grant-Down-Commands			PRESENCE mandatory }|
	{ ID id-Received-Scheduled-EDCH-Power-Share-Value	CRITICALITY ignore	TYPE Received-Scheduled-EDCH-Power-Share-Value	PRESENCE mandatory }|
	{ ID id-Received-Scheduled-EDCH-Power-Share-For-CellPortion-Value 	CRITICALITY ignore	TYPE Received-Scheduled-EDCH-Power-Share-For-CellPortion-Value	PRESENCE mandatory }|
	{ ID id-TUTRANGANSSMeasurementValueInformation 		CRITICALITY ignore	TYPE TUTRANGANSSMeasurementValueInformation	PRESENCE mandatory }|
	{ ID id-EDCH-RACH-Report-Value						CRITICALITY ignore	TYPE EDCH-RACH-Report-Value			PRESENCE mandatory }|
		-- FDD only
	{ ID id-Transmitted-Carrier-Power-For-CellPortion-ValueLCR	CRITICALITY ignore	TYPE Transmitted-Carrier-Power-For-CellPortion-ValueLCR	PRESENCE mandatory }|
	{ ID id-Received-total-wide-band-power-For-CellPortion-ValueLCR	CRITICALITY ignore	TYPE Received-total-wide-band-power-For-CellPortion-ValueLCR	PRESENCE mandatory }|
	{ ID id-TransmittedCarrierPowerOfAllCodesNotUsedForHS-PDSCH-HS-SCCH-E-AGCHOrE-HICHTransmissionCellPortionValue	CRITICALITY ignore	TYPE TransmittedCarrierPowerOfAllCodesNotUsedForHS-PDSCH-HS-SCCH-E-AGCHOrE-HICHTransmissionCellPortionValue		PRESENCE mandatory }|
	{ ID id-UL-TimeslotISCP-For-CellPortion-Value									CRITICALITY ignore	TYPE UL-TimeslotISCP-For-CellPortion-Value									PRESENCE mandatory }|
	{ ID id-HS-DSCHRequiredPowerValueInformation-For-CellPortionLCR	CRITICALITY ignore	TYPE HS-DSCHRequiredPowerValueInformation-For-CellPortionLCR	PRESENCE mandatory }|
	{ ID id-HS-DSCHProvidedBitRateValueInformation-For-CellPortionLCR	CRITICALITY ignore	TYPE HS-DSCHProvidedBitRateValueInformation-For-CellPortionLCR	PRESENCE mandatory }|
	{ ID id-E-DCHProvidedBitRateValueInformation-For-CellPortion					CRITICALITY ignore	TYPE E-DCHProvidedBitRateValueInformation-For-CellPortion										PRESENCE mandatory }|
	{ ID id-UpPTSInterference-For-CellPortion-Value									CRITICALITY ignore	TYPE UpPTSInterference-For-CellPortion-Value									PRESENCE mandatory }
}

CommonMeasurementValueInformation ::= CHOICE {
	measurementAvailable		CommonMeasurementAvailable,
	measurementnotAvailable		CommonMeasurementnotAvailable
}

CommonMeasurementAvailable::= SEQUENCE {
	commonmeasurementValue		CommonMeasurementValue,
	ie-Extensions					ProtocolExtensionContainer { { CommonMeasurementAvailableItem-ExtIEs} }		OPTIONAL,
	...
}

CommonMeasurementAvailableItem-ExtIEs NBAP-PROTOCOL-EXTENSION ::= {
	...
}
CommonMeasurementnotAvailable ::= NULL

CommonPhysicalChannelID ::= INTEGER (0..255)

CommonPhysicalChannelID768 ::= INTEGER (0..511)

Common-PhysicalChannel-Status-Information ::= SEQUENCE {
	commonPhysicalChannelID				CommonPhysicalChannelID,
	resourceOperationalState			ResourceOperationalState,
	availabilityStatus					AvailabilityStatus,
	iE-Extensions						ProtocolExtensionContainer  { { Common-PhysicalChannel-Status-Information-ExtIEs} }		OPTIONAL,
	...
}

Common-PhysicalChannel-Status-Information-ExtIEs NBAP-PROTOCOL-EXTENSION ::= {
	...
}

Common-PhysicalChannel-Status-Information768 ::= SEQUENCE {
	commonPhysicalChannelID768			CommonPhysicalChannelID768,
	resourceOperationalState			ResourceOperationalState,
	availabilityStatus					AvailabilityStatus,
	iE-Extensions						ProtocolExtensionContainer  { { Common-PhysicalChannel-Status-Information768-ExtIEs} }		OPTIONAL,
	...
}

Common-PhysicalChannel-Status-Information768-ExtIEs NBAP-PROTOCOL-EXTENSION ::= {
	...
}


CommonTransportChannelID ::= INTEGER (0..255)

CommonTransportChannel-InformationResponse ::= SEQUENCE {
	commonTransportChannelID			CommonTransportChannelID,
	bindingID							BindingID				OPTIONAL,
	transportLayerAddress				TransportLayerAddress	OPTIONAL,
	iE-Extensions						ProtocolExtensionContainer  { { CommonTransportChannel-InformationResponse-ExtIEs} }		OPTIONAL,
	...
}

CommonTransportChannel-InformationResponse-ExtIEs NBAP-PROTOCOL-EXTENSION ::= {
	{ ID	id-BroadcastCommonTransportBearerIndication	CRITICALITY ignore EXTENSION BroadcastCommonTransportBearerIndication	 PRESENCE optional }|
	{ ID	id-IPMulticastDataBearerIndication			CRITICALITY ignore EXTENSION IPMulticastDataBearerIndication				 PRESENCE optional },
	...
}

Common-TransportChannel-Status-Information ::= SEQUENCE {
	commonTransportChannelID			CommonTransportChannelID,
	resourceOperationalState			ResourceOperationalState,
	availabilityStatus					AvailabilityStatus,
	iE-Extensions						ProtocolExtensionContainer  { { Common-TransportChannel-Status-Information-ExtIEs} }		OPTIONAL,
	...
}

Common-TransportChannel-Status-Information-ExtIEs NBAP-PROTOCOL-EXTENSION ::= {
	...
}

CommunicationControlPortID ::= INTEGER (0..65535)

Compressed-Mode-Deactivation-Flag::= ENUMERATED {
	deactivate,
	maintain-Active
}

ConfigurationGenerationID ::= INTEGER (0..255)
-- Value '0' means "No configuration"

ConstantValue ::= INTEGER (-10..10,...)
-- -10 dB - +10 dB
-- unit dB
-- step 1 dB

ContinuousPacketConnectivityDTX-DRX-Capability ::= ENUMERATED {
	continuous-Packet-Connectivity-DTX-DRX-capable,
	continuous-Packet-Connectivity-DTX-DRX-non-capable
}

ContinuousPacketConnectivityDTX-DRX-Information ::= SEQUENCE {
	uE-DTX-DRX-Offset							UE-DTX-DRX-Offset,
	enabling-Delay								Enabling-Delay,
	dTX-Information								DTX-Information	,
	dRX-Information								DRX-Information							OPTIONAL,
	iE-Extensions								ProtocolExtensionContainer { { ContinuousPacketConnectivityDTX-DRX-Information-ExtIEs } }			OPTIONAL,
	...
}

ContinuousPacketConnectivityDTX-DRX-Information-ExtIEs NBAP-PROTOCOL-EXTENSION ::= {
	...
}

ContinuousPacketConnectivityDTX-DRX-Information-to-Modify ::= SEQUENCE {
	uE-DTX-DRX-Offset							UE-DTX-DRX-Offset						OPTIONAL,
	enabling-Delay								Enabling-Delay							OPTIONAL,
	dTX-Information-to-Modify					DTX-Information-to-Modify				OPTIONAL,
	dRX-Information-to-Modify					DRX-Information-to-Modify				OPTIONAL,
	iE-Extensions								ProtocolExtensionContainer { { ContinuousPacketConnectivityDTX-DRX-Information-to-Modify-ExtIEs } }			OPTIONAL,
	...
}

ContinuousPacketConnectivityDTX-DRX-Information-to-Modify-ExtIEs NBAP-PROTOCOL-EXTENSION ::= {
	...
}


ContinuousPacketConnectivityHS-SCCH-less-Capability ::= ENUMERATED {
	continuous-Packet-Connectivity-HS-SCCH-less-capable,
	continuous-Packet-Connectivity-HS-SCCH-less-capable-non-capable
}


ContinuousPacketConnectivityHS-SCCH-less-Information ::= SEQUENCE (SIZE (1..maxNrOfHS-DSCH-TBSs-HS-SCCHless)) OF ContinuousPacketConnectivityHS-SCCH-less-InformationItem

ContinuousPacketConnectivityHS-SCCH-less-InformationItem ::= SEQUENCE {
	transport-Block-Size-Index				Transport-Block-Size-Index,
	hSPDSCH-Second-Code-Support				HSPDSCH-Second-Code-Support,
	iE-Extensions							ProtocolExtensionContainer { { ContinuousPacketConnectivityHS-SCCH-less-Information-ExtIEs } }			OPTIONAL,
	...
}

ContinuousPacketConnectivityHS-SCCH-less-Information-ExtIEs NBAP-PROTOCOL-EXTENSION ::= {
	...
}


ContinuousPacketConnectivityHS-SCCH-less-Information-Response ::= SEQUENCE {
	hSPDSCH-First-Code-Index				HSPDSCH-First-Code-Index,
	hSPDSCH-Second-Code-Index				HSPDSCH-Second-Code-Index				OPTIONAL,
	iE-Extensions							ProtocolExtensionContainer { { ContinuousPacketConnectivityHS-SCCH-less-Information-Response-ExtIEs } }			OPTIONAL,
	...
}

ContinuousPacketConnectivityHS-SCCH-less-Information-Response-ExtIEs NBAP-PROTOCOL-EXTENSION ::= {
	...
}

ControlGAP ::= INTEGER (1..255)

CPC-Information ::= SEQUENCE {
	continuousPacketConnectivityDTX-DRX-Information					ContinuousPacketConnectivityDTX-DRX-Information						OPTIONAL,
	continuousPacketConnectivityDTX-DRX-Information-to-Modify		ContinuousPacketConnectivityDTX-DRX-Information-to-Modify		OPTIONAL,
	continuousPacketConnectivityHS-SCCH-less-Information			ContinuousPacketConnectivityHS-SCCH-less-Information				OPTIONAL,
	iE-Extensions				ProtocolExtensionContainer { { CPC-Information-ExtIEs} }														OPTIONAL,
	...
}

CPC-Information-ExtIEs NBAP-PROTOCOL-EXTENSION ::= {
	{ ID id-ContinuousPacketConnectivityHS-SCCH-less-Deactivate-Indicator 	CRITICALITY reject	 EXTENSION ContinuousPacketConnectivityHS-SCCH-less-Deactivate-Indicator 	PRESENCE optional},
	...
}

ContinuousPacketConnectivityHS-SCCH-less-Deactivate-Indicator ::= NULL

CQI-DTX-Timer ::= ENUMERATED {v0, v1, v2, v4, v8, v16, v32, v64, v128, v256, v512, infinity}
	-- Unit subframe


CQI-Feedback-Cycle ::= ENUMERATED {v0, v2, v4, v8, v10, v20, v40, v80, v160,..., v16, v32, v64}

CQI-Power-Offset ::= INTEGER (0..8,...)
-- According to mapping in ref. [9] subclause 4.2.1

CQI-RepetitionFactor ::= INTEGER (1..4,...)
-- Step: 1

CriticalityDiagnostics ::= SEQUENCE {
	procedureID					ProcedureID				OPTIONAL,
	triggeringMessage			TriggeringMessage			OPTIONAL,
	procedureCriticality		Criticality				OPTIONAL,
	transactionID				TransactionID				OPTIONAL,
	iEsCriticalityDiagnostics	CriticalityDiagnostics-IE-List	OPTIONAL,
	iE-Extensions				ProtocolExtensionContainer { {CriticalityDiagnostics-ExtIEs} }		OPTIONAL,
	...
}

CriticalityDiagnostics-ExtIEs NBAP-PROTOCOL-EXTENSION ::= {
	...
}

CriticalityDiagnostics-IE-List ::= SEQUENCE (SIZE (1..maxNrOfErrors)) OF
	SEQUENCE {
		iECriticality		Criticality,
		iE-ID				ProtocolIE-ID,
		repetitionNumber	RepetitionNumber0		OPTIONAL,
		iE-Extensions		ProtocolExtensionContainer { {CriticalityDiagnostics-IE-List-ExtIEs} }		OPTIONAL,
		...
	}

CriticalityDiagnostics-IE-List-ExtIEs NBAP-PROTOCOL-EXTENSION ::= {
	{	ID id-MessageStructure		CRITICALITY ignore		EXTENSION MessageStructure		PRESENCE optional	}|
	{	ID id-TypeOfError			CRITICALITY ignore		EXTENSION TypeOfError			PRESENCE mandatory	},
	...
}

CRNC-CommunicationContextID ::= INTEGER (0..1048575)

CSBMeasurementID ::= INTEGER (0..65535)

CSBTransmissionID ::= INTEGER (0..65535)


Common-EDCH-System-InformationLCR ::= SEQUENCE {
	ul-common-E-DCH-MACflow-Specific-InformationLCR			Ul-common-E-DCH-MACflow-Specific-InfoListLCR					OPTIONAL,
	common-E-PUCH-InformationLCR							Common-E-PUCH-InformationLCR							OPTIONAL,
	e-TFCS-Information-TDD									E-TFCS-Information-TDD									OPTIONAL,
	maximum-Number-of-Retransmissions-For-SchedulingInfo		Maximum-Number-of-Retransmissions-For-E-DCH					OPTIONAL,
	eDCH-Retransmission-Timer-SchedulingInfo				E-DCH-MACdFlow-Retransmission-Timer						OPTIONAL,
	iE-Extensions											ProtocolExtensionContainer { { Common-EDCH-System-InformationLCR-ExtIEs } }		OPTIONAL,
	...
}

Common-EDCH-System-InformationLCR-ExtIEs NBAP-PROTOCOL-EXTENSION ::= {
{ ID id-UL-Synchronisation-Parameters-For-FACHLCR				CRITICALITY reject	EXTENSION UL-Synchronisation-Parameters-LCR		PRESENCE optional }|
{ ID id-PhysicalChannelID-for-CommonERNTI-RequestedIndicator	CRITICALITY ignore	EXTENSION PhysicalChannelID-for-CommonERNTI-RequestedIndicator	PRESENCE optional},
	...
}

Common-E-PUCH-InformationLCR ::= SEQUENCE {
	minCR										CodeRate,
	maxCR										CodeRate,
	harqInfo									HARQ-Info-for-E-DCH,
	pRXdes-base-perURAFCN						PRXdes-base-perURAFCN				OPTIONAL,
	e-PUCH-TPC-StepSize							TDD-TPC-UplinkStepSize-LCR			OPTIONAL,
	e-AGCH-TPC-StepSize							TDD-TPC-DownlinkStepSize			OPTIONAL,
	e-PUCH-PowerControlGAP						ControlGAP							OPTIONAL,
	iE-Extensions								ProtocolExtensionContainer { { Common-E-PUCH-InformationLCR-ExtIEs } }		OPTIONAL,
	...
}

Common-E-PUCH-InformationLCR-ExtIEs NBAP-PROTOCOL-EXTENSION ::= {
	...
}

PRXdes-base-perURAFCN ::= SEQUENCE (SIZE (1.. maxFrequencyinCell)) OF PRXdes-base-Item

PRXdes-base-Item ::= SEQUENCE {
	pRXdes-base									PRXdes-base,
	uARFCN										UARFCN											OPTIONAL,
	iE-Extensions							ProtocolExtensionContainer { { PRXdes-base-Item-ExtIEs} }		OPTIONAL,
	...
}

PRXdes-base-Item-ExtIEs  NBAP-PROTOCOL-EXTENSION ::= {
	...
}


Ul-common-E-DCH-MACflow-Specific-InfoListLCR ::= SEQUENCE (SIZE (1..maxNrOfCommonMACFlows)) OF Ul-common-E-DCH-MACflow-Specific-InfoList-ItemLCR

Ul-common-E-DCH-MACflow-Specific-InfoList-ItemLCR		 ::= SEQUENCE {
	ul-Common-MACFlowIDLCR								Common-MACFlow-ID-LCR,
	transportBearerRequestIndicator						TransportBearerRequestIndicator					OPTIONAL,
	bindingID											BindingID										OPTIONAL,
	transportLayerAddress								TransportLayerAddress							OPTIONAL,
	tnlQos												TnlQos											OPTIONAL,
	payloadCRC-PresenceIndicator						PayloadCRC-PresenceIndicator					OPTIONAL,
	common-E-DCH-MACdFlow-Specific-InformationLCR		Common-E-DCH-MACdFlow-Specific-InfoListLCR		OPTIONAL,
	uARFCN												UARFCN											OPTIONAL,
	iE-Extensions										ProtocolExtensionContainer { { Ul-common-E-DCH-MACflow-Specific-InfoList-ItemLCR-ExtIEs} }					OPTIONAL,
	...
}

Ul-common-E-DCH-MACflow-Specific-InfoList-ItemLCR-ExtIEs NBAP-PROTOCOL-EXTENSION ::= {
	...
}

Common-E-DCH-MACdFlow-Specific-InfoListLCR ::= SEQUENCE (SIZE (1.. maxNrOfEDCHMACdFlowsLCR)) OF Common-E-DCH-MACdFlow-Specific-InfoList-ItemLCR

Common-E-DCH-MACdFlow-Specific-InfoList-ItemLCR		 ::= SEQUENCE {
	common-e-DCH-MACdFlow-ID						E-DCH-MACdFlow-ID-LCR,
	maximum-Number-of-Retransmissions-For-E-DCH		Maximum-Number-of-Retransmissions-For-E-DCH			OPTIONAL,
	eDCH-MACdFlow-Multiplexing-List					E-DCH-MACdFlow-Multiplexing-List											OPTIONAL,
	common-E-DCHLogicalChannelInformation			Common-E-DCH-LogicalChannel-InfoList				OPTIONAL,
	eDCH-HARQ-PO-TDD								E-DCH-HARQ-PO-TDD															OPTIONAL,
	eDCH-MACdFlow-Retransmission-Timer				E-DCH-MACdFlow-Retransmission-Timer					OPTIONAL,
	iE-Extensions									ProtocolExtensionContainer { { Common-E-DCH-MACdFlow-Specific-InfoList-ItemLCR-ExtIEs} }				OPTIONAL,
	...
}

Common-E-DCH-MACdFlow-Specific-InfoList-ItemLCR-ExtIEs NBAP-PROTOCOL-EXTENSION ::= {
	...
}



Common-EDCH-System-Information-ResponseLCR ::= SEQUENCE {
	ul-common-E-DCH-MACflow-Specific-InfoResponseLCR			Ul-common-E-DCH-MACflow-Specific-InfoResponseListLCR		OPTIONAL,
	common-E-AGCH-ListLCR										Common-E-AGCH-ListLCR						OPTIONAL,
	common-E-HICH-ListLCR										Common-E-HICH-ListLCR						OPTIONAL,
	common-E-RNTI-Info-LCR										Common-E-RNTI-Info-LCR						OPTIONAL,
	iE-Extensions												ProtocolExtensionContainer { { Common-EDCH-System-Information-ResponseLCR-ExtIEs} }					OPTIONAL,
	...
}

Common-EDCH-System-Information-ResponseLCR-ExtIEs NBAP-PROTOCOL-EXTENSION ::= {
	{ ID id-Ul-common-E-DCH-MACflow-Specific-InfoResponseListLCR-Ext 	CRITICALITY ignore	 EXTENSION Ul-common-E-DCH-MACflow-Specific-InfoResponseListLCR-Ext 	PRESENCE optional},
	...
}

Ul-common-E-DCH-MACflow-Specific-InfoResponseListLCR ::= SEQUENCE (SIZE (1..maxNrOfCommonMACFlows)) OF Ul-common-E-DCH-MACflow-Specific-InfoResponseList-ItemLCR

Ul-common-E-DCH-MACflow-Specific-InfoResponseListLCR-Ext ::= SEQUENCE (SIZE (1..maxNrOfCommonMACFlowsLCRExt)) OF Ul-common-E-DCH-MACflow-Specific-InfoResponseList-ItemLCR

Ul-common-E-DCH-MACflow-Specific-InfoResponseList-ItemLCR ::= SEQUENCE {
	ul-Common-MACFlowID-LCR								Common-MACFlow-ID-LCR,
	bindingID											BindingID										OPTIONAL,
	transportLayerAddress								TransportLayerAddress							OPTIONAL,
	uARFCN												UARFCN											OPTIONAL,
	-- the IE is not used.
	iE-Extensions										ProtocolExtensionContainer { { Ul-common-E-DCH-MACflow-Specific-InfoResponseList-ItemLCR-ExtIEs} }					OPTIONAL,
	...
}

Ul-common-E-DCH-MACflow-Specific-InfoResponseList-ItemLCR-ExtIEs NBAP-PROTOCOL-EXTENSION ::= {
	...
}

Common-E-AGCH-ListLCR ::= SEQUENCE (SIZE (1.. maxNrOfEAGCHsLCR)) OF Common-E-AGCH-ItemLCR

Common-E-AGCH-ItemLCR ::= SEQUENCE {
	e-AGCH-ID									E-AGCH-Id,
	uARFCN										UARFCN											OPTIONAL,
	-- the IE is not used.
	iE-Extensions							ProtocolExtensionContainer { { Common-E-AGCH-ItemLCR-ExtIEs} }		OPTIONAL,
	...
}

Common-E-AGCH-ItemLCR-ExtIEs  NBAP-PROTOCOL-EXTENSION ::= {
	...
}

Common-E-HICH-ListLCR ::= SEQUENCE (SIZE (1.. maxNrOfEHICHsLCR)) OF Common-E-HICH-ItemLCR

Common-E-HICH-ItemLCR ::= SEQUENCE {
	eI										EI,
	e-HICH-ID								E-HICH-ID-LCR,
	iE-Extensions							ProtocolExtensionContainer { { Common-E-HICH-ItemLCR-ExtIEs} }		OPTIONAL,
	...
}

Common-E-HICH-ItemLCR-ExtIEs  NBAP-PROTOCOL-EXTENSION ::= {
	...
}

Common-E-RNTI-Info-LCR ::= SEQUENCE (SIZE (1.. maxnrofERUCCHsLCR)) OF Common-E-RNTI-Info-ItemLCR

Common-E-RNTI-Info-ItemLCR ::= SEQUENCE {
	starting-E-RNTI							E-RNTI,
	number-of-Group							INTEGER(1..32),
	number-of-e-E-RNTI-perGroup				INTEGER(1..7),
	iE-Extensions							ProtocolExtensionContainer { { Common-E-RNTI-Info-ItemLCR-ExtIEs} }		OPTIONAL,
	...
}

Common-E-RNTI-Info-ItemLCR-ExtIEs  NBAP-PROTOCOL-EXTENSION ::= {
{ ID id-AssociatedPhsicalChannelID	CRITICALITY reject		EXTENSION	CommonPhysicalChannelID	PRESENCE optional},
	...
}

Common-MACFlows-to-DeleteLCR ::= SEQUENCE (SIZE (1.. maxNrOfCommonMACFlowsLCR)) OF Common-MACFlows-to-DeleteLCR-Item

Common-MACFlows-to-DeleteLCR-Item ::= SEQUENCE {
	common-MACFlow-ID-LCR							Common-MACFlow-ID-LCR,
	iE-Extensions									ProtocolExtensionContainer { { Common-MACFlows-to-DeleteLCR-Item-ExtIEs} }					OPTIONAL,
	...
}

Common-MACFlows-to-DeleteLCR-Item-ExtIEs NBAP-PROTOCOL-EXTENSION ::= {
	...
}
Common-MACFlow-ID-LCR ::= INTEGER (0..maxNrOfCommonMACFlowsLCR-1)

CommonMACFlow-Specific-InfoListLCR ::= SEQUENCE (SIZE (1.. maxNrOfCommonMACFlowsLCR)) OF CommonMACFlow-Specific-InfoItemLCR

CommonMACFlow-Specific-InfoItemLCR ::= SEQUENCE {
	common-MACFlow-ID-LCR							Common-MACFlow-ID-LCR,
	bindingID										BindingID									OPTIONAL,
	transportLayerAddress							TransportLayerAddress						OPTIONAL,
	tnl-qos											TnlQos										OPTIONAL,
	common-MACFlow-PriorityQueue-InformationLCR		Common-MACFlow-PriorityQueue-Information	OPTIONAL,
	transportBearerRequestIndicator					TransportBearerRequestIndicator				OPTIONAL,
	uARFCN											UARFCN										OPTIONAL,
	iE-Extensions									ProtocolExtensionContainer { { CommonMACFlow-Specific-InfoItemLCR-ExtIEs } }		OPTIONAL,
	...
}

CommonMACFlow-Specific-InfoItemLCR-ExtIEs NBAP-PROTOCOL-EXTENSION ::= {
	...
}



Common-H-RNTI-InformationLCR ::= SEQUENCE (SIZE (1.. maxNoOfCommonH-RNTI)) OF Common-H-RNTI-InfoItemLCR

Common-H-RNTI-InfoItemLCR ::= SEQUENCE {
	common-H-RNTI									HSDSCH-RNTI,
	iE-Extensions									ProtocolExtensionContainer { { Common-H-RNTI-InfoItemLCR-ExtIEs } }		OPTIONAL,
	...
}

Common-H-RNTI-InfoItemLCR-ExtIEs NBAP-PROTOCOL-EXTENSION ::= {
	...
}

Sync-InformationLCR ::= SEQUENCE {
	t-SYNC											T-SYNC,
	t-PROTECT										T-PROTECT,
	n-PROTECT										N-PROTECT,
	iE-Extensions									ProtocolExtensionContainer { { Sync-InformationLCR-ExtIEs } }		OPTIONAL,
	...
}

Sync-InformationLCR-ExtIEs NBAP-PROTOCOL-EXTENSION ::= {
	...
}


CommonMACFlow-Specific-InfoList-ResponseLCR ::= SEQUENCE (SIZE (1..maxNrOfCommonMACFlows)) OF CommonMACFlow-Specific-InfoItem-ResponseLCR

CommonMACFlow-Specific-InfoItem-ResponseLCR ::= SEQUENCE {
	common-MACFlow-ID-LCR								Common-MACFlow-ID-LCR,
	bindingID										BindingID									OPTIONAL,
	transportLayerAddress							TransportLayerAddress						OPTIONAL,
	hSDSCH-Initial-Capacity-Allocation				HSDSCH-Initial-Capacity-Allocation			OPTIONAL,
	iE-Extensions									ProtocolExtensionContainer { { CommonMACFlow-Specific-InfoItem-ResponseLCR-ExtIEs} }			OPTIONAL,
	...
}

CommonMACFlow-Specific-InfoItem-ResponseLCR-ExtIEs NBAP-PROTOCOL-EXTENSION ::= {
	...
}
CPC-InformationLCR ::= SEQUENCE {
	continuousPacketConnectivity-DRX-InformationLCR				ContinuousPacketConnectivity-DRX-InformationLCR							OPTIONAL,
	continuousPacketConnectivity-DRX-Information-to-Modify-LCR		ContinuousPacketConnectivity-DRX-Information-to-Modify-LCR			OPTIONAL,
	hS-DSCH-Semi-PersistentScheduling-Information-LCR			HS-DSCH-Semi-PersistentScheduling-Information-LCR							OPTIONAL,
	hS-DSCH-Semi-PersistentScheduling-Information-to-Modify-LCR	HS-DSCH-Semi-PersistentScheduling-Information-to-Modify-LCR				OPTIONAL,
	hS-DSCH-SPS-Deactivate-Indicator-LCR						NULL		OPTIONAL,
	e-DCH-Semi-PersistentScheduling-Information-LCR				E-DCH-Semi-PersistentScheduling-Information-LCR							OPTIONAL,
	e-DCH-Semi-PersistentScheduling-Information-to-Modify-LCR	E-DCH-Semi-PersistentScheduling-Information-to-Modify-LCR				OPTIONAL,
	e-DCH-SPS-Deactivate-Indicator-LCR							NULL		OPTIONAL,
	iE-Extensions				ProtocolExtensionContainer { { CPC-InformationLCR-ExtIEs} }													OPTIONAL,
	...
}

CPC-InformationLCR-ExtIEs NBAP-PROTOCOL-EXTENSION ::= {
	...
}

ContinuousPacketConnectivity-DRX-CapabilityLCR ::= ENUMERATED {
	continuous-Packet-Connectivity-DRX-Capable,
	continuous-Packet-Connectivity-DRX-Non-Capable
}


ContinuousPacketConnectivity-DRX-InformationLCR ::= SEQUENCE {
	enabling-Delay								Enabling-Delay,
	hS-SCCH-DRX-Information-LCR					HS-SCCH-DRX-Information-LCR,
	e-AGCH-DRX-Information-LCR					E-AGCH-DRX-Information-LCR 			OPTIONAL,
	iE-Extensions								ProtocolExtensionContainer { { ContinuousPacketConnectivity-DRX-InformationLCR-ExtIEs } }			OPTIONAL,
	...
}

ContinuousPacketConnectivity-DRX-InformationLCR-ExtIEs NBAP-PROTOCOL-EXTENSION ::= {
	...
}

HS-SCCH-DRX-Information-LCR ::= SEQUENCE {
	hS-SCCH-UE-DRX-Cycle-LCR									UE-DRX-Cycle-LCR,
	hS-SCCH-Inactivity-Threshold-for-UE-DRX-Cycle-LCR			Inactivity-Threshold-for-UE-DRX-Cycle-LCR			OPTIONAL,
	hS-SCCH-UE-DRX-Offset-LCR									UE-DRX-Offset-LCR,
	iE-Extensions					ProtocolExtensionContainer { { HS-SCCH-DRX-Information-LCR-ExtIEs} } OPTIONAL,
	...
}

HS-SCCH-DRX-Information-LCR-ExtIEs NBAP-PROTOCOL-EXTENSION ::= {
	...
}

E-AGCH-DRX-Information-LCR ::= CHOICE {
	sameAsHS-SCCH				NULL,
	e-AGCH-DRX-Parameters		E-AGCH-DRX-Parameters,
	...
}

E-AGCH-DRX-Parameters ::= SEQUENCE {
	e-AGCH-UE-DRX-Cycle-LCR								UE-DRX-Cycle-LCR,
	e-AGCH-UE-Inactivity-Monitor-Threshold				E-AGCH-UE-Inactivity-Monitor-Threshold			OPTIONAL,
	e-AGCH-UE-DRX-Offset-LCR							UE-DRX-Offset-LCR,
	iE-Extensions										ProtocolExtensionContainer { { E-AGCH-DRX-Parameters-ExtIEs} } OPTIONAL,
	...
}

E-AGCH-DRX-Parameters-ExtIEs NBAP-PROTOCOL-EXTENSION ::= {
	...
}

UE-DRX-Cycle-LCR ::= ENUMERATED {v1, v2, v4, v8, v16, v32, v64,...}
	-- Unit subframe

UE-DRX-Offset-LCR ::= INTEGER (0..63)
	-- Unit subframe

Inactivity-Threshold-for-UE-DRX-Cycle-LCR ::= ENUMERATED {v1, v2, v4, v8, v16, v32, v64,...}
	-- Unit subframe

E-AGCH-UE-Inactivity-Monitor-Threshold ::= ENUMERATED {v0, v1, v2, v4, v8, v16, v32, v64, v128, v256, v512, infinity,...}
	-- Unit subframe

ContinuousPacketConnectivity-DRX-Information-to-Modify-LCR ::= SEQUENCE {
	enabling-Delay								Enabling-Delay							OPTIONAL,
	dRX-Information-to-Modify-LCR				DRX-Information-to-Modify-LCR			OPTIONAL,
	iE-Extensions								ProtocolExtensionContainer { { ContinuousPacketConnectivity-DRX-Information-to-Modify-LCR-ExtIEs } }				OPTIONAL,
	...
}

ContinuousPacketConnectivity-DRX-Information-to-Modify-LCR-ExtIEs NBAP-PROTOCOL-EXTENSION ::= {
	...
}

DRX-Information-to-Modify-LCR ::= CHOICE {
	modify			DRX-Information-to-Modify-Items-LCR,
	deactivate		NULL,
	...
}

DRX-Information-to-Modify-Items-LCR ::= SEQUENCE {
	hS-SCCH-DRX-Information-LCR					HS-SCCH-DRX-Information-LCR			OPTIONAL,
	e-AGCH-DRX-Information-LCR					E-AGCH-DRX-Information-LCR			OPTIONAL,
	iE-Extensions								ProtocolExtensionContainer { {DRX-Information-to-Modify-Items-LCR-ExtIEs} } OPTIONAL,
	...
}

DRX-Information-to-Modify-Items-LCR-ExtIEs NBAP-PROTOCOL-EXTENSION ::= {
	...
}

ContinuousPacketConnectivity-DRX-Information-ResponseLCR ::= SEQUENCE {
	enabling-Delay							Enabling-Delay							OPTIONAL,
	hS-SCCH-DRX-Information-ResponseLCR		HS-SCCH-DRX-Information-ResponseLCR		OPTIONAL,
	e-AGCH-DRX-Information-ResponseLCR		E-AGCH-DRX-Information-ResponseLCR		OPTIONAL,
	iE-Extensions							ProtocolExtensionContainer { { ContinuousPacketConnectivity-DRX-Information-ResponseLCR-ExtIEs } }			OPTIONAL,
	...
}

ContinuousPacketConnectivity-DRX-Information-ResponseLCR-ExtIEs NBAP-PROTOCOL-EXTENSION ::= {
	...
}

HS-SCCH-DRX-Information-ResponseLCR ::= SEQUENCE {
	hS-SCCH-UE-DRX-Cycle-LCR									UE-DRX-Cycle-LCR		OPTIONAL,
	hS-SCCH-Inactivity-Threshold-for-UE-DRX-Cycle-LCR			Inactivity-Threshold-for-UE-DRX-Cycle-LCR		OPTIONAL,
	hS-SCCH-UE-DRX-Offset-LCR									UE-DRX-Offset-LCR		OPTIONAL,
	iE-Extensions					ProtocolExtensionContainer { { HS-SCCH-DRX-Information-ResponseLCR-ExtIEs} } OPTIONAL,
	...
}

HS-SCCH-DRX-Information-ResponseLCR-ExtIEs NBAP-PROTOCOL-EXTENSION ::= {
	...
}

E-AGCH-DRX-Information-ResponseLCR ::= CHOICE {
	sameAsHS-SCCH						NULL,
	e-AGCH-DRX-Parameters-Response		E-AGCH-DRX-Parameters-Response,
	...
}

E-AGCH-DRX-Parameters-Response ::= SEQUENCE {
	e-AGCH-UE-DRX-Cycle-LCR							UE-DRX-Cycle-LCR						OPTIONAL,
	e-AGCH-UE-Inactivity-Monitor-Threshold			E-AGCH-UE-Inactivity-Monitor-Threshold	OPTIONAL,
	e-AGCH-UE-DRX-Offset-LCR						UE-DRX-Offset-LCR						OPTIONAL,
	iE-Extensions									ProtocolExtensionContainer { { E-AGCH-DRX-Parameters-Response-ExtIEs} } OPTIONAL,
	...
}

E-AGCH-DRX-Parameters-Response-ExtIEs NBAP-PROTOCOL-EXTENSION ::= {
	...
}



-- ==========================================
--	D
-- ==========================================



DATA-ID ::= INTEGER (0..3)

DCH-ID ::= INTEGER (0..255)

DCH-FDD-Information ::= SEQUENCE (SIZE (1..maxNrOfDCHs)) OF DCH-FDD-InformationItem

DCH-FDD-InformationItem ::= SEQUENCE {
	payloadCRC-PresenceIndicator		PayloadCRC-PresenceIndicator,
	ul-FP-Mode							UL-FP-Mode,
	toAWS								ToAWS,
	toAWE								ToAWE,
	dCH-SpecificInformationList			DCH-Specific-FDD-InformationList,
	iE-Extensions						ProtocolExtensionContainer { { DCH-FDD-InformationItem-ExtIEs} }	OPTIONAL,
	...
}

DCH-FDD-InformationItem-ExtIEs NBAP-PROTOCOL-EXTENSION ::= {
	{ ID id-TnlQos						CRITICALITY ignore		EXTENSION TnlQos		PRESENCE optional	},
	...
}

DCH-Specific-FDD-InformationList ::= SEQUENCE (SIZE (1..maxNrOfDCHs)) OF DCH-Specific-FDD-Item

DCH-Specific-FDD-Item ::=	SEQUENCE {
	dCH-ID								DCH-ID,
	ul-TransportFormatSet				TransportFormatSet,
	dl-TransportFormatSet				TransportFormatSet,
	allocationRetentionPriority			AllocationRetentionPriority,
	frameHandlingPriority				FrameHandlingPriority,
	qE-Selector							QE-Selector,
	iE-Extensions						ProtocolExtensionContainer { { DCH-Specific-FDD-Item-ExtIEs} }	OPTIONAL,
	...
}

DCH-Specific-FDD-Item-ExtIEs NBAP-PROTOCOL-EXTENSION ::= {
	{ ID id-Unidirectional-DCH-Indicator	CRITICALITY reject	EXTENSION Unidirectional-DCH-Indicator	PRESENCE optional	},
	...
}

DCH-Indicator-For-E-DCH-HSDPA-Operation ::= ENUMERATED {
	dch-not-present
}

DCH-InformationResponse ::= SEQUENCE (SIZE (1..maxNrOfDCHs)) OF DCH-InformationResponseItem

DCH-InformationResponseItem ::= SEQUENCE {
	dCH-ID											DCH-ID,
	bindingID										BindingID				OPTIONAL,
	transportLayerAddress							TransportLayerAddress	OPTIONAL,
	iE-Extensions									ProtocolExtensionContainer { { DCH-InformationResponseItem-ExtIEs} }		OPTIONAL,
	...
}

DCH-InformationResponseItem-ExtIEs NBAP-PROTOCOL-EXTENSION ::= {
	{ ID id-TransportBearerNotSetupIndicator	CRITICALITY ignore	EXTENSION TransportBearerNotSetupIndicator		PRESENCE optional	}, -- FDD only
	...
}

DCH-MeasurementOccasion-Information ::= SEQUENCE (SIZE (1.. maxNrOfDCHMeasurementOccasionPatternSequence)) OF DchMeasurementOccasionInformation-Item

DchMeasurementOccasionInformation-Item ::= SEQUENCE {
	pattern-Sequence-Identifier					Pattern-Sequence-Identifier,
	status-Flag									Status-Flag,
	measurement-Occasion-Pattern-Sequence-parameters					Measurement-Occasion-Pattern-Sequence-parameters 			OPTIONAL,
	iE-Extensions								ProtocolExtensionContainer { { DCH-MeasurementOccasion-Information-ExtIEs } }			OPTIONAL,
	...
}

DCH-MeasurementOccasion-Information-ExtIEs NBAP-PROTOCOL-EXTENSION ::= {
	...
}

Measurement-Occasion-Pattern-Sequence-parameters ::= SEQUENCE {
	measurement-Occasion-Pattern-Sequence-parameters-k					INTEGER(1..9),
	measurement-Occasion-Pattern-Sequence-parameters-offset				INTEGER(0..511),
	measurement-Occasion-Pattern-Sequence-parameters-M-Length			INTEGER(1..512),
	measurement-Occasion-Pattern-Sequence-parameters-Timeslot-Bitmap	BIT STRING (SIZE (7)),
	iE-Extensions				ProtocolExtensionContainer { { Measurement-Occasion-Pattern-Sequence-parameters-ExtIEs } } OPTIONAL,
	...
}

Measurement-Occasion-Pattern-Sequence-parameters-ExtIEs NBAP-PROTOCOL-EXTENSION ::= {
	...
}

DCH-TDD-Information ::= SEQUENCE (SIZE (1..maxNrOfDCHs)) OF DCH-TDD-InformationItem

DCH-TDD-InformationItem ::= SEQUENCE {
	payloadCRC-PresenceIndicator		PayloadCRC-PresenceIndicator,
	ul-FP-Mode							UL-FP-Mode,
	toAWS								ToAWS,
	toAWE								ToAWE,
	dCH-SpecificInformationList			DCH-Specific-TDD-InformationList,
	iE-Extensions							ProtocolExtensionContainer { { DCH-TDD-InformationItem-ExtIEs} }		OPTIONAL,
	...
}

DCH-TDD-InformationItem-ExtIEs NBAP-PROTOCOL-EXTENSION ::= {
	{ID id-TnlQos						CRITICALITY ignore		EXTENSION TnlQos		PRESENCE optional},
	...
}

DCH-Specific-TDD-InformationList ::= SEQUENCE (SIZE (1..maxNrOfDCHs)) OF DCH-Specific-TDD-Item

DCH-Specific-TDD-Item ::=	SEQUENCE {
	dCH-ID									DCH-ID,
	ul-CCTrCH-ID							CCTrCH-ID,
	dl-CCTrCH-ID							CCTrCH-ID,
	ul-TransportFormatSet					TransportFormatSet,
	dl-TransportFormatSet					TransportFormatSet,
	allocationRetentionPriority				AllocationRetentionPriority,
	frameHandlingPriority					FrameHandlingPriority,
	qE-Selector								QE-Selector						OPTIONAL,
	-- This IE shall be present if DCH is part of set of Coordinated DCHs
	iE-Extensions							ProtocolExtensionContainer { { DCH-Specific-TDD-Item-ExtIEs} }		OPTIONAL,
	...
}

DCH-Specific-TDD-Item-ExtIEs NBAP-PROTOCOL-EXTENSION ::= {
	{ ID id-Unidirectional-DCH-Indicator	CRITICALITY reject	EXTENSION Unidirectional-DCH-Indicator	PRESENCE optional	},
	...
}

FDD-DCHs-to-Modify ::= SEQUENCE (SIZE (1..maxNrOfDCHs)) OF FDD-DCHs-to-ModifyItem

FDD-DCHs-to-ModifyItem	 ::= SEQUENCE {
	ul-FP-Mode							UL-FP-Mode		OPTIONAL,
	toAWS								ToAWS			OPTIONAL,
	toAWE								ToAWE			OPTIONAL,
	transportBearerRequestIndicator		TransportBearerRequestIndicator,
	dCH-SpecificInformationList			DCH-ModifySpecificInformation-FDD,
	iE-Extensions						ProtocolExtensionContainer { { FDD-DCHs-to-ModifyItem-ExtIEs} }		OPTIONAL,
	...
}

FDD-DCHs-to-ModifyItem-ExtIEs  NBAP-PROTOCOL-EXTENSION ::= {
	{ID id-TnlQos						CRITICALITY ignore		EXTENSION TnlQos		PRESENCE optional},
	...
}

DCH-ModifySpecificInformation-FDD::= SEQUENCE (SIZE (1..maxNrOfDCHs)) OF DCH-ModifySpecificItem-FDD

DCH-ModifySpecificItem-FDD::=	SEQUENCE {
	dCH-ID											DCH-ID,
	ul-TransportFormatSet							TransportFormatSet			OPTIONAL,
	dl-TransportFormatSet							TransportFormatSet			OPTIONAL,
	allocationRetentionPriority						AllocationRetentionPriority	OPTIONAL,
	frameHandlingPriority							FrameHandlingPriority		OPTIONAL,
	iE-Extensions									ProtocolExtensionContainer { { DCH-ModifySpecificItem-FDD-ExtIEs} }		OPTIONAL,
	...
}

DCH-ModifySpecificItem-FDD-ExtIEs  NBAP-PROTOCOL-EXTENSION ::= {
	{ID id-Unidirectional-DCH-Indicator					CRITICALITY reject		EXTENSION Unidirectional-DCH-Indicator		PRESENCE optional},
	...
}


TDD-DCHs-to-Modify ::= SEQUENCE (SIZE (1..maxNrOfDCHs)) OF DCH-ModifyItem-TDD

DCH-ModifyItem-TDD ::= SEQUENCE {
	ul-FP-Mode							UL-FP-Mode		OPTIONAL,
	toAWS								ToAWS			OPTIONAL,
	toAWE								ToAWE			OPTIONAL,
	transportBearerRequestIndicator		TransportBearerRequestIndicator,
	dCH-SpecificInformationList			DCH-ModifySpecificInformation-TDD,
	iE-Extensions						ProtocolExtensionContainer { { TDD-DCHs-to-ModifyItem-ExtIEs} }			OPTIONAL,
	...
}

TDD-DCHs-to-ModifyItem-ExtIEs  NBAP-PROTOCOL-EXTENSION ::= {
	{ID id-TnlQos						CRITICALITY ignore		EXTENSION TnlQos		PRESENCE optional},
	...
}

DCH-ModifySpecificInformation-TDD ::= SEQUENCE (SIZE (1..maxNrOfDCHs)) OF DCH-ModifySpecificItem-TDD

DCH-ModifySpecificItem-TDD ::=	SEQUENCE {
	dCH-ID											DCH-ID,
	ul-CCTrCH-ID									CCTrCH-ID					OPTIONAL,
	dl-CCTrCH-ID									CCTrCH-ID					OPTIONAL,
	ul-TransportFormatSet							TransportFormatSet			OPTIONAL,
	dl-TransportFormatSet							TransportFormatSet			OPTIONAL,
	allocationRetentionPriority						AllocationRetentionPriority	OPTIONAL,
	frameHandlingPriority							FrameHandlingPriority		OPTIONAL,
	iE-Extensions									ProtocolExtensionContainer { { DCH-ModifySpecificItem-TDD-ExtIEs} }			OPTIONAL,
	...
}

DCH-ModifySpecificItem-TDD-ExtIEs  NBAP-PROTOCOL-EXTENSION ::= {
	...
}

DedicatedChannelsCapacityConsumptionLaw ::= SEQUENCE ( SIZE(1..maxNrOfSF) ) OF
	SEQUENCE {
		dl-Cost-1		INTEGER (0..65535),
		dl-Cost-2		INTEGER (0..65535),
		ul-Cost-1		INTEGER (0..65535),
		ul-Cost-2		INTEGER (0..65535),
		iE-Extensions		ProtocolExtensionContainer { { DedicatedChannelsCapacityConsumptionLaw-ExtIEs } }		OPTIONAL,
	...
}

DedicatedChannelsCapacityConsumptionLaw-ExtIEs NBAP-PROTOCOL-EXTENSION ::= {
	...
}

DedicatedMeasurementType ::= ENUMERATED {
	sir,
	sir-error,
	transmitted-code-power,
	rscp,
	rx-timing-deviation,
	round-trip-time,
	...,
	rx-timing-deviation-LCR,
	angle-Of-Arrival-LCR,
	hs-sich-quality,
	best-Cell-Portions,
	rx-timing-deviation-768,
	rx-timing-deviation-384-extended,
	best-Cell-PortionsLCR

}

DedicatedMeasurementValue ::= CHOICE {
	sIR-Value						SIR-Value,
	sIR-ErrorValue					SIR-Error-Value,
	transmittedCodePowerValue			Transmitted-Code-Power-Value,
	rSCP								RSCP-Value,
	rxTimingDeviationValue				Rx-Timing-Deviation-Value,
	roundTripTime						Round-Trip-Time-Value,
	...,
	extension-DedicatedMeasurementValue		Extension-DedicatedMeasurementValue
}

Extension-DedicatedMeasurementValue	::= ProtocolIE-Single-Container {{ Extension-DedicatedMeasurementValueIE }}

Extension-DedicatedMeasurementValueIE NBAP-PROTOCOL-IES ::= {
	{ ID id-Rx-Timing-Deviation-Value-LCR	CRITICALITY reject	TYPE Rx-Timing-Deviation-Value-LCR				PRESENCE mandatory }|
	{ ID id-Angle-Of-Arrival-Value-LCR			CRITICALITY reject	TYPE Angle-Of-Arrival-Value-LCR				PRESENCE mandatory }|
	{ ID id-HS-SICH-Reception-Quality			CRITICALITY reject	TYPE HS-SICH-Reception-Quality-Value		PRESENCE mandatory }|
	{ ID id-Best-Cell-Portions-Value			CRITICALITY reject	TYPE Best-Cell-Portions-Value					PRESENCE mandatory }|
	{ ID id-Rx-Timing-Deviation-Value-768		CRITICALITY reject	TYPE Rx-Timing-Deviation-Value-768			PRESENCE mandatory }|
	{ ID id-Rx-Timing-Deviation-Value-384-ext	CRITICALITY reject	TYPE Rx-Timing-Deviation-Value-384-ext		PRESENCE mandatory }|
	{ ID id-Extended-Round-Trip-Time-Value		CRITICALITY reject	TYPE Extended-Round-Trip-Time-Value			PRESENCE mandatory }|
	{ ID id-Best-Cell-Portions-ValueLCR			CRITICALITY reject	TYPE Best-Cell-Portions-ValueLCR				PRESENCE mandatory },
	...
}

DedicatedMeasurementValueInformation ::= CHOICE {
	measurementAvailable		DedicatedMeasurementAvailable,
	measurementnotAvailable		DedicatedMeasurementnotAvailable
}

DedicatedMeasurementAvailable::= SEQUENCE {
	dedicatedmeasurementValue		DedicatedMeasurementValue,
    cFN                             CFN							OPTIONAL,
	ie-Extensions					ProtocolExtensionContainer { { DedicatedMeasurementAvailableItem-ExtIEs} }		OPTIONAL,
	...
}

DedicatedMeasurementAvailableItem-ExtIEs NBAP-PROTOCOL-EXTENSION ::= {
	...
}

DedicatedMeasurementnotAvailable ::= NULL

DelayedActivation ::= CHOICE {
	cfn						CFN,
	separate-indication		NULL
}

DelayedActivationUpdate ::= CHOICE {
	activate		Activate-Info,
	deactivate		Deactivate-Info
}

Activate-Info ::= SEQUENCE {
	activation-type  		Execution-Type,
	initial-dl-tx-power 	DL-Power,
	firstRLS-Indicator		FirstRLS-Indicator											OPTIONAL, --FDD Only
	propagation-delay		PropagationDelay 											OPTIONAL, --FDD Only
	iE-Extensions			ProtocolExtensionContainer { { Activate-Info-ExtIEs} }		OPTIONAL,
	...
}

Activate-Info-ExtIEs NBAP-PROTOCOL-EXTENSION ::= {
	{ ID id-ExtendedPropagationDelay	CRITICALITY reject	EXTENSION ExtendedPropagationDelay		PRESENCE mandatory }, --FDD Only
	...
}

Deactivate-Info ::= SEQUENCE {
	deactivation-type  		Execution-Type,
	iE-Extensions			ProtocolExtensionContainer { { Deactivate-Info-ExtIEs} }		OPTIONAL,
	...
}

Deactivate-Info-ExtIEs NBAP-PROTOCOL-EXTENSION ::= {
	...
}

Execution-Type ::= CHOICE {
	synchronised 	CFN,
	unsynchronised	NULL
}

DeltaSIR				::= INTEGER (0..30)
-- Unit dB, Step 0.1 dB, Range 0..3 dB.

DGANSSCorrections ::= SEQUENCE {
	dGANSS-ReferenceTime				INTEGER(0..119),
	dGANSS-Information					DGANSS-Information,
	ie-Extensions						ProtocolExtensionContainer { { DGANSSCorrections-ExtIEs } }	OPTIONAL,
	...
}

DGANSSCorrections-ExtIEs NBAP-PROTOCOL-EXTENSION ::= {
	...
}

DGANSS-Corrections-Req ::= SEQUENCE {
	dGANSS-Signal-ID					BIT STRING (SIZE (8)),
	ie-Extensions		 				ProtocolExtensionContainer { { DGANSS-Corrections-Req-ExtIEs } }	OPTIONAL,
	...
}

DGANSS-Corrections-Req-ExtIEs NBAP-PROTOCOL-EXTENSION ::= {
	{ID id-GANSS-ID				CRITICALITY	ignore	EXTENSION	GANSS-ID			PRESENCE	optional},
	...
}

DGANSS-Information ::= SEQUENCE (SIZE (1..maxSgnType)) OF DGANSS-InformationItem

DGANSS-InformationItem ::= SEQUENCE {
	gANSS-SignalId						GANSS-Signal-ID												OPTIONAL,
	gANSS-StatusHealth					GANSS-StatusHealth,
-- The following IE shall be present if the Status Health IE value is not equal to "no data" or "invalid data"
	dGANSS-SignalInformation			DGANSS-SignalInformation									OPTIONAL,
	ie-Extensions		 				ProtocolExtensionContainer { { DGANSS-InformationItem-ExtIEs } }	OPTIONAL,
	...
}

DGANSS-InformationItem-ExtIEs NBAP-PROTOCOL-EXTENSION ::= {
	...
}

DGANSS-SignalInformation ::= SEQUENCE (SIZE (1..maxGANSSSat)) OF DGANSS-SignalInformationItem

DGANSS-SignalInformationItem ::= SEQUENCE {
	satId								INTEGER(0..63),
	gANSS-iod							BIT STRING (SIZE (10)),
	udre								UDRE,
	ganss-prc							INTEGER(-2047..2047),
	ganss-rrc							INTEGER(-127..127),
	ie-Extensions						ProtocolExtensionContainer { { DGANSS-SignalInformationItem-ExtIEs } }	OPTIONAL,
	...
}

DGANSS-SignalInformationItem-ExtIEs NBAP-PROTOCOL-EXTENSION ::= {
	{ID id-DGNSS-ValidityPeriod	CRITICALITY	ignore	EXTENSION	DGNSS-ValidityPeriod	PRESENCE	optional},
	...
}

DGANSSThreshold ::= SEQUENCE {
	pRCDeviation						PRCDeviation,
	ie-Extensions						ProtocolExtensionContainer { { DGANSSThreshold-ExtIEs } }	OPTIONAL,
	...
}

DGANSSThreshold-ExtIEs NBAP-PROTOCOL-EXTENSION ::= {
	...
}

DGNSS-ValidityPeriod ::= 			SEQUENCE {
	udreGrowthRate						UDREGrowthRate,
	udreValidityTime					UDREValidityTime,
	iE-Extensions						ProtocolExtensionContainer { { DGNSS-ValidityPeriod-ExtIEs } }		OPTIONAL,
	...
}

DGNSS-ValidityPeriod-ExtIEs NBAP-PROTOCOL-EXTENSION ::= {
	...
}

DGPSCorrections ::= SEQUENCE {
   gpstow                GPSTOW,
   status-health         GPS-Status-Health,
   satelliteinfo         SAT-Info-DGPSCorrections,
   ie-Extensions		 ProtocolExtensionContainer { { DGPSCorrections-ExtIEs} }		OPTIONAL,
   ...
}

DGPSCorrections-ExtIEs NBAP-PROTOCOL-EXTENSION ::= {
	...
}

DGPSThresholds ::= SEQUENCE {
   prcdeviation         PRCDeviation,
   ie-Extensions		ProtocolExtensionContainer { { DGPSThresholds-ExtIEs} }		OPTIONAL,
   ...
}

DGPSThresholds-ExtIEs NBAP-PROTOCOL-EXTENSION ::= {
	...
}

DiscardTimer ::= ENUMERATED {v20,v40,v60,v80,v100,v120,v140,v160,v180,v200,v250,v300,v400,v500,v750,v1000,v1250,v1500,v1750,v2000,v2500,v3000,v3500,v4000,v4500,v5000,v7500,
 ...
}

DiversityControlField ::= ENUMERATED {
	may,
	must,
	must-not,
	...
}

DiversityMode ::= ENUMERATED {
	none,
	sTTD,
	closed-loop-mode1,
	not-used-closed-loop-mode2,
	...
}

DL-DPCH-SlotFormat ::= INTEGER (0..16,...)

DL-DPCH-TimingAdjustment ::= ENUMERATED {
	timing-advance,
	timing-delay
}

DL-Timeslot-Information ::= SEQUENCE (SIZE (1.. maxNrOfDLTSs)) OF DL-Timeslot-InformationItem

DL-Timeslot-InformationItem	 ::= SEQUENCE {
	timeSlot								TimeSlot,
	midambleShiftAndBurstType				MidambleShiftAndBurstType,
	tFCI-Presence							TFCI-Presence,
	dL-Code-Information						TDD-DL-Code-Information,
	iE-Extensions							ProtocolExtensionContainer { { DL-Timeslot-InformationItem-ExtIEs} }		OPTIONAL,
	...
}

DL-Timeslot-InformationItem-ExtIEs NBAP-PROTOCOL-EXTENSION ::= {
	...
}

DL-TimeslotLCR-Information ::= SEQUENCE (SIZE (1.. maxNrOfDLTSLCRs)) OF DL-TimeslotLCR-InformationItem

DL-TimeslotLCR-InformationItem	 ::= SEQUENCE {
	timeSlotLCR								TimeSlotLCR,
	midambleShiftLCR						MidambleShiftLCR,
	tFCI-Presence							TFCI-Presence,
	dL-Code-LCR-Information					TDD-DL-Code-LCR-Information,
	iE-Extensions							ProtocolExtensionContainer { { DL-TimeslotLCR-InformationItem-ExtIEs} }		OPTIONAL,
	...
}

DL-TimeslotLCR-InformationItem-ExtIEs NBAP-PROTOCOL-EXTENSION ::= {
	{ ID id-Initial-DL-Power-TimeslotLCR-InformationItem	CRITICALITY ignore   EXTENSION DL-Power		PRESENCE optional	}|
	-- Applicable to 1.28Mcps TDD only
	{ ID id-Maximum-DL-Power-TimeslotLCR-InformationItem	CRITICALITY ignore   EXTENSION DL-Power		PRESENCE optional	}|
	-- Applicable to 1.28Mcps TDD only
	{ ID id-Minimum-DL-Power-TimeslotLCR-InformationItem	CRITICALITY ignore 	EXTENSION DL-Power		PRESENCE optional	},
	-- Applicable to 1.28Mcps TDD only
	...
}

DL-Timeslot768-Information ::= SEQUENCE (SIZE (1.. maxNrOfDLTSs)) OF DL-Timeslot768-InformationItem

DL-Timeslot768-InformationItem	 ::= SEQUENCE {
	timeSlot								TimeSlot,
	midambleShiftAndBurstType768			MidambleShiftAndBurstType768,
	tFCI-Presence							TFCI-Presence,
	dL-Code-768-Information					TDD-DL-Code-768-Information,
	iE-Extensions							ProtocolExtensionContainer { { DL-Timeslot768-InformationItem-ExtIEs} }		OPTIONAL,
	...
}

DL-Timeslot768-InformationItem-ExtIEs NBAP-PROTOCOL-EXTENSION ::= {
	...
}

DL-FrameType ::= ENUMERATED {
	typeA,
	typeB,
	...
}

DL-or-Global-CapacityCredit ::= INTEGER (0..65535)

DL-Power ::= INTEGER (-350..150)
-- Value = DL-Power/10
-- Unit dB, Range -35dB .. +15dB, Step +0.1dB

DLPowerAveragingWindowSize ::= INTEGER (1..60)

DL-PowerBalancing-Information ::= SEQUENCE {
	powerAdjustmentType					PowerAdjustmentType,
    dLReferencePower					DL-Power		OPTIONAL,
	-- This IE shall be present if Power Adjustment Type IE equals to 'Common'
	dLReferencePowerList-DL-PC-Rqst		DL-ReferencePowerInformationList		OPTIONAL,
	-- This IE shall be present if Power Adjustment Type IE equals to 'Individual'
	maxAdjustmentStep					MaxAdjustmentStep		OPTIONAL,
	-- This IE shall be present if Power Adjustment Type IE equals to 'Common' or 'Individual'
	adjustmentPeriod					AdjustmentPeriod		OPTIONAL,
	-- This IE shall be present if Power Adjustment Type IE equals to 'Common' or 'Individual'
	adjustmentRatio						ScaledAdjustmentRatio	OPTIONAL,
	-- This IE shall be present if Power Adjustment Type IE equals to 'Common' or 'Individual'
	iE-Extensions						ProtocolExtensionContainer { { DL-PowerBalancing-Information-ExtIEs } } OPTIONAL,
	...
}

DL-PowerBalancing-Information-ExtIEs NBAP-PROTOCOL-EXTENSION ::= {
	...
}

DL-ReferencePowerInformationList 		::= SEQUENCE (SIZE (1..maxNrOfRLs)) OF DL-ReferencePowerInformationItem

DL-ReferencePowerInformationItem ::= SEQUENCE {
	rL-ID						RL-ID,
	dl-Reference-Power			DL-Power,
	iE-Extensions				ProtocolExtensionContainer { {DL-ReferencePowerInformationItem-ExtIEs} } OPTIONAL,
	...
}

DL-ReferencePowerInformationItem-ExtIEs NBAP-PROTOCOL-EXTENSION ::= {
	...
}

DL-PowerBalancing-ActivationIndicator	::= ENUMERATED {
	dL-PowerBalancing-Activated
}

DL-PowerBalancing-UpdatedIndicator	::= ENUMERATED {
	dL-PowerBalancing-Updated
}

DL-ScramblingCode ::= INTEGER (0..15)
-- 0= Primary scrambling code of the cell, 1..15= Secondary scrambling code --

DL-TimeslotISCP ::= INTEGER (0..91)

DL-TimeslotISCPInfo ::= SEQUENCE (SIZE (1..maxNrOfDLTSs)) OF DL-TimeslotISCPInfoItem

DL-TimeslotISCPInfoItem ::= SEQUENCE {
	timeSlot					TimeSlot,
	dL-TimeslotISCP				DL-TimeslotISCP,
	iE-Extensions				ProtocolExtensionContainer { {DL-TimeslotISCPInfoItem-ExtIEs} }			OPTIONAL,
	...
	}

DL-TimeslotISCPInfoItem-ExtIEs  NBAP-PROTOCOL-EXTENSION ::= {
	...
}

DL-TimeslotISCPInfoLCR ::= SEQUENCE (SIZE (1..maxNrOfDLTSLCRs)) OF DL-TimeslotISCPInfoItemLCR

DL-TimeslotISCPInfoItemLCR ::= SEQUENCE {
	timeSlotLCR					TimeSlotLCR,
	dL-TimeslotISCP				DL-TimeslotISCP,
	iE-Extensions				ProtocolExtensionContainer { {DL-TimeslotISCPInfoItemLCR-ExtIEs} }			OPTIONAL,
	...
	}

DL-TimeslotISCPInfoItemLCR-ExtIEs  NBAP-PROTOCOL-EXTENSION ::= {
	...
}

DL-TPC-Pattern01Count ::= INTEGER (0..30,...)

DLTransmissionBranchLoadValue ::= INTEGER (0..101,...)

Downlink-Compressed-Mode-Method 	::= ENUMERATED {
	not-Used-puncturing,
	sFdiv2,
	higher-layer-scheduling,
	...
}

DL-HS-PDSCH-Timeslot-Information-LCR-PSCH-ReconfRqst ::= SEQUENCE (SIZE (1..maxNrOfDLTSLCRs)) OF DL-HS-PDSCH-Timeslot-InformationItem-LCR-PSCH-ReconfRqst

DL-HS-PDSCH-Timeslot-InformationItem-LCR-PSCH-ReconfRqst::= SEQUENCE {
	timeSlot									TimeSlotLCR,
	midambleShiftAndBurstType					MidambleShiftLCR,
	dl-HS-PDSCH-Codelist-LCR-PSCH-ReconfRqst		DL-HS-PDSCH-Codelist-LCR-PSCH-ReconfRqst,
	maxHSDSCH-HSSCCH-Power						MaximumTransmissionPower					OPTIONAL,
	iE-Extensions								ProtocolExtensionContainer { { DL-HS-PDSCH-Timeslot-InformationItem-LCR-PSCH-ReconfRqst-ExtIEs} }		OPTIONAL,
	...
}

DL-HS-PDSCH-Timeslot-InformationItem-LCR-PSCH-ReconfRqst-ExtIEs NBAP-PROTOCOL-EXTENSION ::= {
	{ ID id-MaxHSDSCH-HSSCCH-Power-per-CELLPORTION						CRITICALITY ignore		EXTENSION MaxHSDSCH-HSSCCH-Power-per-CELLPORTION					PRESENCE optional},
	...
}

MaxHSDSCH-HSSCCH-Power-per-CELLPORTION ::= SEQUENCE (SIZE (1..maxNrOfCellPortionsPerCellLCR)) OF MaxHSDSCH-HSSCCH-Power-per-CELLPORTION-Item

MaxHSDSCH-HSSCCH-Power-per-CELLPORTION-Item::= SEQUENCE {
	cellPortionLCRID							CellPortionLCRID,
	maxHSDSCH-HSSCCH-Power						MaximumTransmissionPower,
	iE-Extensions								ProtocolExtensionContainer { { MaxHSDSCH-HSSCCH-Power-per-CELLPORTION-Item-ExtIEs} }		OPTIONAL,
	...
}

MaxHSDSCH-HSSCCH-Power-per-CELLPORTION-Item-ExtIEs NBAP-PROTOCOL-EXTENSION ::= {
	...
}

DL-HS-PDSCH-Codelist-LCR-PSCH-ReconfRqst ::= SEQUENCE (SIZE (1..maxNrOfHSPDSCHs)) OF TDD-ChannelisationCode

DPC-Mode ::= ENUMERATED {
	mode0,
	mode1,
	...
}

DPCH-ID ::= INTEGER (0..239)

DPCH-ID768 ::= INTEGER (0..479)

DRX-Information ::= SEQUENCE {
	uE-DRX-Cycle							UE-DRX-Cycle,
	inactivity-Threshold-for-UE-DRX-Cycle							Inactivity-Threshold-for-UE-DRX-Cycle,
	inactivity-Threshold-for-UE-Grant-Monitoring					Inactivity-Threshold-for-UE-Grant-Monitoring,
	uE-DRX-Grant-Monitoring 				UE-DRX-Grant-Monitoring,
	iE-Extensions							ProtocolExtensionContainer { {DRX-Information-ExtIEs} } OPTIONAL,
	...
}

DRX-Information-ExtIEs NBAP-PROTOCOL-EXTENSION ::= {
	...
}

DRX-Information-to-Modify ::= CHOICE {
	modify			DRX-Information-to-Modify-Items,
	deactivate		NULL,
	...
}

DRX-Information-to-Modify-Items ::= SEQUENCE {
	uE-DRX-Cycle													UE-DRX-Cycle											OPTIONAL,
	inactivity-Threshold-for-UE-DRX-Cycle							Inactivity-Threshold-for-UE-DRX-Cycle				OPTIONAL,
	inactivity-Threshold-for-UE-Grant-Monitoring					Inactivity-Threshold-for-UE-Grant-Monitoring		OPTIONAL,
	uE-DRX-Grant-Monitoring 										UE-DRX-Grant-Monitoring									OPTIONAL,
	iE-Extensions								 ProtocolExtensionContainer { {DRX-Information-to-Modify-Items-ExtIEs} } OPTIONAL,
	...
}

DRX-Information-to-Modify-Items-ExtIEs NBAP-PROTOCOL-EXTENSION ::= {
	...
}


DRX-Interruption-by-HS-DSCH ::= ENUMERATED {
	drx-Interruption-Configured,
	drx-Interruption-Not-Configured,
	...
}

DSCH-ID ::= INTEGER (0..255)

DSCH-InformationResponse ::= SEQUENCE (SIZE (1..maxNrOfDSCHs)) OF DSCH-InformationResponseItem

DSCH-InformationResponseItem ::= SEQUENCE {
	dSCH-ID											DSCH-ID,
	bindingID										BindingID					OPTIONAL,
	transportLayerAddress							TransportLayerAddress		OPTIONAL,
	iE-Extensions									ProtocolExtensionContainer { { DSCH-InformationResponseItem-ExtIEs } }		OPTIONAL,
	...
}

DSCH-InformationResponseItem-ExtIEs NBAP-PROTOCOL-EXTENSION ::= {
	...
}

DSCH-TDD-Information ::= SEQUENCE (SIZE (1..maxNrOfDSCHs)) OF DSCH-TDD-InformationItem

DSCH-TDD-InformationItem ::= SEQUENCE {
	dSCH-ID									DSCH-ID,
	cCTrCH-ID								CCTrCH-ID,
	transportFormatSet						TransportFormatSet,
	allocationRetentionPriority				AllocationRetentionPriority,
	frameHandlingPriority					FrameHandlingPriority,
	toAWS									ToAWS,
	toAWE									ToAWE,
	iE-Extensions							ProtocolExtensionContainer { { DSCH-TDD-InformationItem-ExtIEs} }		OPTIONAL,
	...
}

DSCH-TDD-InformationItem-ExtIEs NBAP-PROTOCOL-EXTENSION ::= {
	{ ID id-bindingID					CRITICALITY	ignore		EXTENSION 	BindingID				PRESENCE optional	}|
	-- Shall be ignored if bearer establishment with ALCAP.
	{ ID id-transportlayeraddress		CRITICALITY	ignore		EXTENSION 	TransportLayerAddress	PRESENCE optional	}|
	-- Shall be ignored if bearer establishment with ALCAP.
	{ ID id-TnlQos						CRITICALITY ignore		EXTENSION TnlQos					PRESENCE optional},
	...
}

DsField ::= BIT STRING (SIZE (8))

DTX-Cycle-2ms-Items ::= SEQUENCE {
	uE-DTX-Cycle1-2ms				UE-DTX-Cycle1-2ms,
	uE-DTX-Cycle2-2ms				UE-DTX-Cycle2-2ms,
	mAC-DTX-Cycle-2ms				MAC-DTX-Cycle-2ms,
	iE-Extensions								ProtocolExtensionContainer { { DTX-Cycle-2ms-Items-ExtIEs} }			OPTIONAL,
	...
}

DTX-Cycle-2ms-Items-ExtIEs NBAP-PROTOCOL-EXTENSION ::= {
	...
}

DTX-Cycle-2ms-to-Modify-Items ::= SEQUENCE {
	uE-DTX-Cycle1-2ms				UE-DTX-Cycle1-2ms,
	uE-DTX-Cycle2-2ms				UE-DTX-Cycle2-2ms,
	mAC-DTX-Cycle-2ms				MAC-DTX-Cycle-2ms,
	iE-Extensions								ProtocolExtensionContainer { { DTX-Cycle-2ms-to-Modify-Items-ExtIEs} }			OPTIONAL,
	...
}

DTX-Cycle-2ms-to-Modify-Items-ExtIEs NBAP-PROTOCOL-EXTENSION ::= {
	...
}

DTX-Cycle-10ms-Items ::= SEQUENCE {
	uE-DTX-Cycle1-10ms				UE-DTX-Cycle1-10ms,
	uE-DTX-Cycle2-10ms				UE-DTX-Cycle2-10ms,
	mAC-DTX-Cycle-10ms				MAC-DTX-Cycle-10ms,
	iE-Extensions								ProtocolExtensionContainer { { DTX-Cycle-10ms-Items-ExtIEs} }			OPTIONAL,
	...
}

DTX-Cycle-10ms-Items-ExtIEs NBAP-PROTOCOL-EXTENSION ::= {
	...
}

DTX-Cycle-10ms-to-Modify-Items ::= SEQUENCE {
	uE-DTX-Cycle1-10ms				UE-DTX-Cycle1-10ms,
	uE-DTX-Cycle2-10ms				UE-DTX-Cycle2-10ms,
	mAC-DTX-Cycle-10ms				MAC-DTX-Cycle-10ms,
	iE-Extensions								ProtocolExtensionContainer { { DTX-Cycle-10ms-to-Modify-Items-ExtIEs} }			OPTIONAL,
	...
}

DTX-Cycle-10ms-to-Modify-Items-ExtIEs NBAP-PROTOCOL-EXTENSION ::= {
	...
}

DTX-Information ::= SEQUENCE {
	e-DCH-TTI-Length					E-DCH-TTI-Length,
	inactivity-Threshold-for-UE-DTX-Cycle2					Inactivity-Threshold-for-UE-DTX-Cycle2,
	uE-DTX-Long-Preamble 				UE-DTX-Long-Preamble,
	mAC-Inactivity-Threshold				MAC-Inactivity-Threshold	,
	cQI-DTX-Timer 				CQI-DTX-Timer,
	uE-DPCCH-burst1				UE-DPCCH-burst1,
	uE-DPCCH-burst2				UE-DPCCH-burst2,
	iE-Extensions				ProtocolExtensionContainer { {DTX-Information-ExtIEs} } OPTIONAL,
	...
}

DTX-Information-ExtIEs NBAP-PROTOCOL-EXTENSION ::= {
	...
}


DTX-Information-to-Modify ::= CHOICE {
	modify			DTX-Information-to-Modify-Items,
	deactivate		NULL,
	...
}

DTX-Information-to-Modify-Items ::= SEQUENCE {
	e-DCH-TTI-Length-to-Modify		E-DCH-TTI-Length-to-Modify			OPTIONAL,
	inactivity-Threshold-for-UE-DTX-Cycle2					Inactivity-Threshold-for-UE-DTX-Cycle2					OPTIONAL,
	uE-DTX-Long-Preamble 			UE-DTX-Long-Preamble				OPTIONAL,
	mAC-Inactivity-Threshold			MAC-Inactivity-Threshold				OPTIONAL,
	cQI-DTX-Timer 					CQI-DTX-Timer						OPTIONAL,
	uE-DPCCH-burst1					UE-DPCCH-burst1					OPTIONAL,
	uE-DPCCH-burst2					UE-DPCCH-burst2						OPTIONAL,
	iE-Extensions					ProtocolExtensionContainer { {DTX-Information-to-Modify-Items-ExtIEs} } OPTIONAL,
	...
}

DTX-Information-to-Modify-Items-ExtIEs NBAP-PROTOCOL-EXTENSION ::= {
	...
}

Dual-Band-Capability ::= ENUMERATED {
	dual-Band-Capable,
	dual-Band-non-Capable
}

Dual-Band-Capability-Info::= SEQUENCE {
	dual-Band-Capability										Dual-Band-Capability,
	possible-Secondary-Serving-Cell-List						Possible-Secondary-Serving-Cell-List		OPTIONAL,
	iE-Extensions				ProtocolExtensionContainer { { Dual-Band-Capability-Info-ExtIEs } }		OPTIONAL,
	...
}

Dual-Band-Capability-Info-ExtIEs NBAP-PROTOCOL-EXTENSION ::= {
	...
}


DwPCH-Power ::= INTEGER (-150..400,...)
-- DwPCH-power = power * 10
-- If power <= -15 DwPCH shall be set to -150
-- If power >= 40 DwPCH shall be set to 400
-- Unit dBm, Range -15dBm .. +40 dBm, Step +0.1dB


-- ==========================================
--	E
-- ==========================================

E-AGCH-Table-Choice ::= ENUMERATED{table16B, table16B-1, ...}

E-AGCH-FDD-Code-Information ::= CHOICE {
	replace					E-AGCH-FDD-Code-List,
	remove					NULL,
	...
}

E-AGCH-FDD-Code-List ::= SEQUENCE (SIZE (1..maxNrOfE-AGCHs)) OF FDD-DL-ChannelisationCodeNumber

E-AI-Capability ::= ENUMERATED {
	e-AI-capable,
	e-AI-non-capable
}

E-AI-Indicator ::= BOOLEAN


E-DCH-Capability ::= ENUMERATED {
	e-DCH-capable,
	e-DCH-non-capable
}

E-DCHCapacityConsumptionLaw ::= SEQUENCE {
		e-DCH-SF-allocation 	E-DCH-SF-allocation,
		dl-Cost-1				INTEGER (0..65535)														OPTIONAL,
		dl-Cost-2				INTEGER (0..65535)														OPTIONAL,
		iE-Extensions			ProtocolExtensionContainer { { E-DCHCapacityConsumptionLaw-ExtIEs } }		OPTIONAL,
	...
}

E-DCHCapacityConsumptionLaw-ExtIEs NBAP-PROTOCOL-EXTENSION ::= {
	...
}

E-DCH-TDD-CapacityConsumptionLaw ::= SEQUENCE {
		ul-Cost				INTEGER (0..65535),
		dl-Cost				INTEGER (0..65535)														OPTIONAL,
		iE-Extensions			ProtocolExtensionContainer { { E-DCH-TDD-CapacityConsumptionLaw-ExtIEs } }		OPTIONAL,
	...
}

E-DCH-TDD-CapacityConsumptionLaw-ExtIEs NBAP-PROTOCOL-EXTENSION ::= {
	...
}

E-DCH-SF-allocation ::= SEQUENCE ( SIZE(1..maxNrOfCombEDPDCH) ) OF
	SEQUENCE {
		ul-Cost-1		INTEGER (0..65535),
		ul-Cost-2		INTEGER (0..65535),
		iE-Extensions		ProtocolExtensionContainer { { E-DCH-SF-allocation-ExtIEs } }		OPTIONAL,
	...
}

E-DCH-SF-allocation-ExtIEs NBAP-PROTOCOL-EXTENSION ::= {
	...
}

E-DCH-TTI2ms-Capability ::= BOOLEAN
-- True = TTI 10ms and 2ms supported for E-DCH False = only TTI 10ms supported for E-DCH

E-DCH-SF-Capability ::= ENUMERATED {
	sf64,
	sf32,
	sf16,
	sf8,
	sf4,
	sf4x2,
	sf2x2,
	sf4x2-and-sf2x2,
	...
}

E-DCH-HARQ-Combining-Capability ::= ENUMERATED {
	iR-Combining-capable,
	chase-Combining-capable,
	iR-and-Chase-Combining-capable
}

E-DCH-DDI-Value ::= INTEGER (0..62)

E-DCH-FDD-DL-Control-Channel-Information ::= SEQUENCE {
	e-AGCH-And-E-RGCH-E-HICH-FDD-Scrambling-Code	DL-ScramblingCode															OPTIONAL,
	e-AGCH-Channelisation-Code						FDD-DL-ChannelisationCodeNumber												OPTIONAL,
	primary-e-RNTI									E-RNTI																		OPTIONAL,
	secondary-e-RNTI								E-RNTI																		OPTIONAL,
	e-RGCH-E-HICH-Channelisation-Code				FDD-DL-ChannelisationCodeNumber												OPTIONAL,
	e-RGCH-Signature-Sequence						E-RGCH-Signature-Sequence													OPTIONAL,
	e-HICH-Signature-Sequence						E-HICH-Signature-Sequence													OPTIONAL,
	serving-Grant-Value								E-Serving-Grant-Value														OPTIONAL,
	primary-Secondary-Grant-Selector				E-Primary-Secondary-Grant-Selector											OPTIONAL,
	e-RGCH-Release-Indicator						E-RGCH-Release-Indicator														OPTIONAL,
	iE-Extensions									ProtocolExtensionContainer { { E-DCH-FDD-DL-Control-Channel-Information-ExtIEs} }		OPTIONAL,
	...
}

E-DCH-FDD-DL-Control-Channel-Information-ExtIEs NBAP-PROTOCOL-EXTENSION ::= {
	{ ID id-Default-Serving-Grant-in-DTX-Cycle2		CRITICALITY ignore		EXTENSION E-Serving-Grant-Value			PRESENCE optional },
	...
}

E-DCH-FDD-Information ::= SEQUENCE {
	e-DCH-MACdFlows-Information						E-DCH-MACdFlows-Information,
	hARQ-Process-Allocation-Scheduled-2ms-EDCH		HARQ-Process-Allocation-2ms-EDCH											OPTIONAL,
	e-DCH-Maximum-Bitrate							E-DCH-Maximum-Bitrate														OPTIONAL,
	e-DCH-Processing-Overload-Level					E-DCH-Processing-Overload-Level												OPTIONAL,
	e-DCH-Reference-Power-Offset					E-DCH-Reference-Power-Offset												OPTIONAL,
	iE-Extensions									ProtocolExtensionContainer { { E-DCH-FDD-Information-ExtIEs} }								OPTIONAL,
	...
}

E-DCH-FDD-Information-ExtIEs NBAP-PROTOCOL-EXTENSION ::= {
	{ ID id-E-DCH-PowerOffset-for-SchedulingInfo		CRITICALITY ignore	EXTENSION	E-DCH-PowerOffset-for-SchedulingInfo		PRESENCE optional}|
	{ ID id-SixteenQAM-UL-Operation-Indicator			CRITICALITY reject	EXTENSION	SixteenQAM-UL-Operation-Indicator			PRESENCE optional}|
	{ ID id-E-AGCH-Table-Choice							CRITICALITY ignore	EXTENSION	E-AGCH-Table-Choice				PRESENCE conditional},
	-- The IE shall be present if the SixteenQAM UL Operation Indicator IE is set to "Activate"--
	...
}

E-DCH-FDD-Information-Response ::= SEQUENCE {
	e-DCH-MACdFlow-Specific-InformationResp			E-DCH-MACdFlow-Specific-InformationResp										OPTIONAL,
	hARQ-Process-Allocation-Scheduled-2ms-EDCH		HARQ-Process-Allocation-2ms-EDCH																	OPTIONAL,
	iE-Extensions									ProtocolExtensionContainer { { E-DCH-FDD-Information-Response-ExtIEs } }					OPTIONAL,
	...
}

E-DCH-FDD-Information-Response-ExtIEs NBAP-PROTOCOL-EXTENSION ::= {
	...
}

E-DCH-FDD-Information-to-Modify ::= SEQUENCE {
	e-DCH-MACdFlow-Specific-Info-to-Modify			E-DCH-MACdFlow-Specific-InfoList-to-Modify															OPTIONAL,
	hARQ-Process-Allocation-Scheduled-2ms-EDCH		HARQ-Process-Allocation-2ms-EDCH																	OPTIONAL,
	e-DCH-Maximum-Bitrate							E-DCH-Maximum-Bitrate																				OPTIONAL,
	e-DCH-Processing-Overload-Level					E-DCH-Processing-Overload-Level																		OPTIONAL,
	e-DCH-Reference-Power-Offset					E-DCH-Reference-Power-Offset												OPTIONAL,
	mACeReset-Indicator								MACeReset-Indicator															OPTIONAL,
	iE-Extensions									ProtocolExtensionContainer { { E-DCH-FDD-Information-to-Modify-ExtIEs} }					OPTIONAL,
	...
}

E-DCH-FDD-Information-to-Modify-ExtIEs NBAP-PROTOCOL-EXTENSION ::= {
	{ ID id-E-DCH-PowerOffset-for-SchedulingInfo		CRITICALITY ignore	EXTENSION	E-DCH-PowerOffset-for-SchedulingInfo							PRESENCE optional}|
	{ ID id-SixteenQAM-UL-Operation-Indicator			CRITICALITY reject	EXTENSION	SixteenQAM-UL-Operation-Indicator								PRESENCE optional}|
	{ ID id-E-DCH-MACdPDUSizeFormat 					CRITICALITY reject	EXTENSION	E-DCH-MACdPDUSizeFormat 										PRESENCE optional}|
	{ ID id-E-DCH-DL-Control-Channel-Grant-Information	CRITICALITY ignore	EXTENSION	E-DCH-DL-Control-Channel-Grant-Information						PRESENCE optional}|
	{ ID id-E-AGCH-Table-Choice							CRITICALITY ignore	EXTENSION	E-AGCH-Table-Choice										PRESENCE conditional},
	-- The IE shall be present if the SixteenQAM UL Operation Indicator IE is set to "Activate"--
	...
}

E-DCH-FDD-Update-Information ::= SEQUENCE {
	e-DCH-MACdFlow-Specific-UpdateInformation		E-DCH-MACdFlow-Specific-UpdateInformation									OPTIONAL,
	hARQ-Process-Allocation-Scheduled-2ms-EDCH		HARQ-Process-Allocation-2ms-EDCH																	OPTIONAL,
	iE-Extensions									ProtocolExtensionContainer { { E-DCH-FDD-Update-Information-ExtIEs } }					OPTIONAL,
	...
}

E-DCH-FDD-Update-Information-ExtIEs NBAP-PROTOCOL-EXTENSION ::= {
	{ ID id-E-DCH-DL-Control-Channel-Change-Information			CRITICALITY ignore	EXTENSION	E-DCH-DL-Control-Channel-Change-Information			PRESENCE optional},
	...
}


E-DCH-MACdFlow-Specific-UpdateInformation ::= SEQUENCE (SIZE (1..maxNrOfEDCHMACdFlows)) OF E-DCH-MACdFlow-Specific-UpdateInformation-Item

E-DCH-MACdFlow-Specific-UpdateInformation-Item ::= SEQUENCE {
	e-DCH-MACdFlow-ID								E-DCH-MACdFlow-ID,
	hARQ-Process-Allocation-NonSched-2ms-EDCH		HARQ-Process-Allocation-2ms-EDCH																	OPTIONAL,
	iE-Extensions									ProtocolExtensionContainer { { E-DCH-MACdFlow-Specific-UpdateInformation-Item-ExtIEs} }	OPTIONAL,
	...
}

E-DCH-MACdFlow-Specific-UpdateInformation-Item-ExtIEs NBAP-PROTOCOL-EXTENSION ::= {
	...
}

E-DCH-DL-Control-Channel-Change-Information ::= SEQUENCE (SIZE (1..maxNrOfEDCHRLs)) OF E-DCH-DL-Control-Channel-Change-Information-Item

E-DCH-DL-Control-Channel-Change-Information-Item ::= SEQUENCE {
	e-DCH-RL-ID								RL-ID,
	iE-Extensions							ProtocolExtensionContainer { { E-DCH-DL-Control-Channel-Change-Information-Item-ExtIEs} }	OPTIONAL,
	...
}

E-DCH-DL-Control-Channel-Change-Information-Item-ExtIEs NBAP-PROTOCOL-EXTENSION ::= {
	...
}

E-DCH-DL-Control-Channel-Grant-Information ::= SEQUENCE (SIZE (1..maxNrOfEDCHRLs)) OF E-DCH-DL-Control-Channel-Grant-Information-Item

E-DCH-DL-Control-Channel-Grant-Information-Item ::= SEQUENCE {
	e-DCH-RL-ID								RL-ID,
	iE-Extensions							ProtocolExtensionContainer { { E-DCH-DL-Control-Channel-Grant-Information-Item-ExtIEs} }	OPTIONAL,
	...
}

E-DCH-DL-Control-Channel-Grant-Information-Item-ExtIEs NBAP-PROTOCOL-EXTENSION ::= {
	...
}

E-DCH-Grant-Type-Information ::= CHOICE {
	e-DCH-Non-Scheduled-Transmission-Grant		E-DCH-Non-Scheduled-Transmission-Grant-Items,
	e-DCH-Scheduled-Transmission-Grant			NULL,
	...
}

E-DCH-LogicalChannelInformation ::= SEQUENCE (SIZE (1..maxNoOfLogicalChannels)) OF E-DCH-LogicalChannelInformationItem

E-DCH-LogicalChannelInformationItem ::= SEQUENCE {
	logicalChannelId				LogicalChannelID,
	schedulingPriorityIndicator		SchedulingPriorityIndicator,
	schedulingInformation			SchedulingInformation,
	mACesGuaranteedBitRate			MACesGuaranteedBitRate		OPTIONAL,
	e-DCH-DDI-Value					E-DCH-DDI-Value,
	mACd-PDU-Size-List				E-DCH-MACdPDU-SizeList,
	iE-Extensions					ProtocolExtensionContainer { { E-DCH-LogicalChannelInformationItem-ExtIEs } }			OPTIONAL,
	...
}

E-DCH-LogicalChannelInformationItem-ExtIEs NBAP-PROTOCOL-EXTENSION ::= {
	{ ID id-MaximumMACdPDU-SizeExtended 	CRITICALITY reject		EXTENSION	MAC-PDU-SizeExtended 		PRESENCE optional}|
	{ ID id-MACes-Maximum-Bitrate-LCR		CRITICALITY ignore		EXTENSION	MACes-Maximum-Bitrate-LCR		PRESENCE optional}| --1.28Mcps TDD only
	{ ID id-UE-AggregateMaximumBitRate-Enforcement-Indicator	CRITICALITY ignore	EXTENSION	UE-AggregateMaximumBitRate-Enforcement-Indicator	PRESENCE optional},
	...
}

E-DCH-Maximum-Bitrate ::= INTEGER (0..5742,...,5743..11498)

E-DCH-PowerOffset-for-SchedulingInfo ::= INTEGER (0.. maxNrOfEDCH-HARQ-PO-QUANTSTEPs)

E-DCH-Processing-Overload-Level ::= INTEGER (0..10,...)

E-DCH-Reference-Power-Offset ::= INTEGER (0.. maxNrOfEDCH-HARQ-PO-QUANTSTEPs)

E-DCH-MACdPDU-SizeList ::= SEQUENCE (SIZE (1.. maxNrOfMACdPDUSize)) OF E-DCH-MACdPDU-SizeListItem

E-DCH-MACdPDU-SizeListItem ::= SEQUENCE {
	mACdPDU-Size					MACdPDU-Size,
	iE-Extensions					ProtocolExtensionContainer { { E-DCH-MACdPDU-SizeListItem-ExtIEs } }			OPTIONAL,
	...
}

E-DCH-MACdPDU-SizeListItem-ExtIEs NBAP-PROTOCOL-EXTENSION ::= {
	...
}

E-DCH-MACdPDU-SizeCapability ::= ENUMERATED {
	fixedSizeCapable,
	flexibleSizeCapable
}

E-DCH-MACdPDUSizeFormat ::= ENUMERATED {
	fixedMACdPDU-Size,
	flexibleMACdPDU-Size
}


E-DCH-LogicalChannelToModify ::= SEQUENCE (SIZE (1..maxNoOfLogicalChannels)) OF E-DCH-LogicalChannelToModifyItem

E-DCH-LogicalChannelToModifyItem ::= SEQUENCE {
	logicalChannelId				LogicalChannelID,
	schedulingPriorityIndicator		SchedulingPriorityIndicator		OPTIONAL,
	schedulingInformation			SchedulingInformation		OPTIONAL,
	mACesGuaranteedBitRate			MACesGuaranteedBitRate		OPTIONAL,
	e-DCH-DDI-Value					E-DCH-DDI-Value					OPTIONAL,
	mACd-PDU-Size-List				E-DCH-MACdPDU-SizeToModifyList,
	iE-Extensions					ProtocolExtensionContainer { { E-DCH-LogicalChannelToModifyItem-ExtIEs } }			OPTIONAL,
	...
}

E-DCH-LogicalChannelToModifyItem-ExtIEs NBAP-PROTOCOL-EXTENSION ::= {
	{ ID id-MaximumMACdPDU-SizeExtended 	CRITICALITY reject		EXTENSION	MAC-PDU-SizeExtended 	PRESENCE optional}|
	{ ID id-MACes-Maximum-Bitrate-LCR		CRITICALITY ignore		EXTENSION	MACes-Maximum-Bitrate-LCR		PRESENCE optional}, --1.28Mcps TDD only
	...
}

E-DCH-MACdPDU-SizeToModifyList ::= SEQUENCE (SIZE (0.. maxNrOfMACdPDUSize)) OF E-DCH-MACdPDU-SizeListItem



E-DCH-LogicalChannelToDelete ::= SEQUENCE (SIZE (1..maxNoOfLogicalChannels)) OF E-DCH-LogicalChannelToDeleteItem

E-DCH-LogicalChannelToDeleteItem ::= SEQUENCE {
	logicalChannelId				LogicalChannelID,
	iE-Extensions					ProtocolExtensionContainer { { E-DCH-LogicalChannelToDeleteItem-ExtIEs } }			OPTIONAL,
	...
}

E-DCH-LogicalChannelToDeleteItem-ExtIEs NBAP-PROTOCOL-EXTENSION ::= {
	...
}

LogicalChannelID ::= INTEGER (1..15)


E-DCH-HARQ-PO-FDD ::= INTEGER (0.. maxNrOfEDCH-HARQ-PO-QUANTSTEPs)

E-DCH-MACdFlow-ID ::= INTEGER (0..maxNrOfEDCHMACdFlows-1)

E-DCH-MACdFlows-Information ::= SEQUENCE {
	e-DCH-MACdFlow-Specific-Info					E-DCH-MACdFlow-Specific-InfoList,
	iE-Extensions									ProtocolExtensionContainer { { E-DCH-MACdFlows-Information-ExtIEs} }						OPTIONAL,
	...
}

E-DCH-MACdFlows-Information-ExtIEs NBAP-PROTOCOL-EXTENSION ::= {
	...
}

E-DCH-MACdFlow-Multiplexing-List ::= BIT STRING ( SIZE(maxNrOfEDCHMACdFlows) )

E-DCH-MACdFlow-Specific-InfoList ::= SEQUENCE (SIZE (1..maxNrOfEDCHMACdFlows)) OF E-DCH-MACdFlow-Specific-InfoItem

E-DCH-MACdFlow-Specific-InfoItem ::= SEQUENCE {
	e-DCH-MACdFlow-ID								E-DCH-MACdFlow-ID,
	allocationRetentionPriority						AllocationRetentionPriority,
	tnlQos											TnlQos																		OPTIONAL,
	payloadCRC-PresenceIndicator					PayloadCRC-PresenceIndicator,
	maximum-Number-of-Retransmissions-For-E-DCH		Maximum-Number-of-Retransmissions-For-E-DCH,
	eDCH-HARQ-PO-FDD								E-DCH-HARQ-PO-FDD,
	eDCH-MACdFlow-Multiplexing-List					E-DCH-MACdFlow-Multiplexing-List																	OPTIONAL,
	eDCH-Grant-Type-Information						E-DCH-Grant-Type-Information,
	bundlingModeIndicator							BundlingModeIndicator														OPTIONAL,
	eDCHLogicalChannelInformation					E-DCH-LogicalChannelInformation,
	iE-Extensions									ProtocolExtensionContainer { { E-DCH-MACdFlow-Specific-InfoItem-ExtIEs} }				OPTIONAL,
	...
}

E-DCH-MACdFlow-Specific-InfoItem-ExtIEs NBAP-PROTOCOL-EXTENSION ::= {
	{ ID id-TransportBearerNotRequestedIndicator	CRITICALITY ignore	EXTENSION TransportBearerNotRequestedIndicator		PRESENCE optional	},
	...
}

E-DCH-MACdFlow-Specific-InformationResp ::= SEQUENCE (SIZE (1..maxNrOfEDCHMACdFlows)) OF E-DCH-MACdFlow-Specific-InformationResp-Item

E-DCH-MACdFlow-Specific-InformationResp-Item ::= SEQUENCE {
	e-DCH-MACdFlow-ID								E-DCH-MACdFlow-ID,
	bindingID										BindingID																	OPTIONAL,
	transportLayerAddress							TransportLayerAddress														OPTIONAL,
	hARQ-Process-Allocation-NonSched-2ms-EDCH		HARQ-Process-Allocation-2ms-EDCH																	OPTIONAL,
	iE-Extensions									ProtocolExtensionContainer { { E-DCH-MACdFlow-Specific-InformationResp-Item-ExtIEs} }	OPTIONAL,
	...
}

E-DCH-MACdFlow-Specific-InformationResp-Item-ExtIEs NBAP-PROTOCOL-EXTENSION ::= {
	{ ID id-TransportBearerNotSetupIndicator	CRITICALITY ignore	EXTENSION TransportBearerNotSetupIndicator		PRESENCE optional	}, -- FDD only
	...
}

E-DCH-MACdFlow-Specific-InfoList-to-Modify ::= SEQUENCE (SIZE (1..maxNrOfEDCHMACdFlows)) OF E-DCH-MACdFlow-Specific-InfoItem-to-Modify

E-DCH-MACdFlow-Specific-InfoItem-to-Modify ::= SEQUENCE {
	e-DCH-MACdFlow-ID								E-DCH-MACdFlow-ID,
	allocationRetentionPriority						AllocationRetentionPriority													OPTIONAL,
	transportBearerRequestIndicator					TransportBearerRequestIndicator,
	tnlQos											TnlQos																		OPTIONAL,
	maximum-Number-of-Retransmissions-For-E-DCH		Maximum-Number-of-Retransmissions-For-E-DCH									OPTIONAL,
	eDCH-HARQ-PO-FDD								E-DCH-HARQ-PO-FDD																					OPTIONAL,
	eDCH-MACdFlow-Multiplexing-List					E-DCH-MACdFlow-Multiplexing-List																	OPTIONAL,
	eDCH-Grant-Type-Information						E-DCH-Grant-Type-Information																		OPTIONAL,
	bundlingModeIndicator							BundlingModeIndicator																				OPTIONAL,
	eDCH-LogicalChannelToAdd						E-DCH-LogicalChannelInformation																		OPTIONAL,
	eDCH-LogicalChannelToModify						E-DCH-LogicalChannelToModify																		OPTIONAL,
	eDCH-LogicalChannelToDelete						E-DCH-LogicalChannelToDelete																		OPTIONAL,
	iE-Extensions									ProtocolExtensionContainer { { E-DCH-MACdFlow-Specific-InfoItem-to-Modify-ExtIEs} }		OPTIONAL,
	...
}

E-DCH-MACdFlow-Specific-InfoItem-to-Modify-ExtIEs NBAP-PROTOCOL-EXTENSION ::= {
	...
}

E-DCH-MACdFlows-to-Delete ::= SEQUENCE (SIZE (1..maxNrOfEDCHMACdFlows)) OF E-DCH-MACdFlow-to-Delete-Item

E-DCH-MACdFlow-to-Delete-Item ::= SEQUENCE {
	e-DCH-MACdFlow-ID								E-DCH-MACdFlow-ID,
	iE-Extensions									ProtocolExtensionContainer { { E-DCH-MACdFlow-to-Delete-Item-ExtIEs} }					OPTIONAL,
	...
}

E-DCH-MACdFlow-to-Delete-Item-ExtIEs NBAP-PROTOCOL-EXTENSION ::= {
	...
}

E-DCH-Non-Scheduled-Transmission-Grant-Items ::= SEQUENCE {
	-- The following IE shall be ignored if id-Ext-Max-Bits-MACe-PDU-non-scheduled is present in E-DCH-Non-Scheduled-Transmission-Grant-Items-ExtIEs
	maxBits-MACe-PDU-non-scheduled				Max-Bits-MACe-PDU-non-scheduled,
	hARQ-Process-Allocation-NonSched-2ms		HARQ-Process-Allocation-2ms-EDCH												OPTIONAL,
	iE-Extensions								ProtocolExtensionContainer { { E-DCH-Non-Scheduled-Transmission-Grant-Items-ExtIEs} }		OPTIONAL,
	...
}

E-DCH-Non-Scheduled-Transmission-Grant-Items-ExtIEs NBAP-PROTOCOL-EXTENSION ::= {
	-- The following IE shall be present if the maximum number of bits to be signalled exceeds maxNrOfBits-MACe-PDU-non-scheduled
	{ ID id-Ext-Max-Bits-MACe-PDU-non-scheduled		CRITICALITY reject		EXTENSION	Ext-Max-Bits-MACe-PDU-non-scheduled		PRESENCE optional},
	...
}

E-DCH-Non-serving-Relative-Grant-Down-Commands ::= INTEGER (0..100,...)

E-DCHProvidedBitRateValue ::= INTEGER(0..16777215,...,16777216..256000000)
-- Unit bit/s, Range 0..2^24-1..2^24..256,000,000, Step 1 bit

Maximum-Target-ReceivedTotalWideBandPower ::= INTEGER (0..621)
-- mapping as for RTWP measurement value, as specified in [22]

Target-NonServing-EDCH-To-Total-EDCH-Power-Ratio ::= INTEGER (0..100)
-- Unit %, Range 0..100%, Step 1%

E-DCH-RL-Indication ::= ENUMERATED {
	e-DCH,
	non-e-DCH
}


E-DCH-Serving-Cell-Change-Info-Response ::= SEQUENCE {
	e-DCH-serving-cell-choice		E-DCH-serving-cell-choice,
	iE-Extensions					ProtocolExtensionContainer { { E-DCH-serving-cell-informationResponse-ExtIEs} } OPTIONAL,
	...
}

E-DCH-serving-cell-informationResponse-ExtIEs NBAP-PROTOCOL-EXTENSION ::= {
	...
}

E-DCH-serving-cell-choice ::= CHOICE {
	e-DCH-serving-cell-change-successful		E-DCH-serving-cell-change-successful,
	e-DCH-serving-cell-change-unsuccessful		E-DCH-serving-cell-change-unsuccessful,
	...
}

E-DCH-serving-cell-change-successful ::= SEQUENCE {
	e-DCH-RL-InformationList-Rsp			E-DCH-RL-InformationList-Rsp,
	iE-Extensions						ProtocolExtensionContainer { { E-DCH-serving-cell-change-successful-ExtIEs} } OPTIONAL,
	...
}

E-DCH-RL-InformationList-Rsp ::= SEQUENCE (SIZE (0..maxNrOfRLs)) OF E-DCH-RL-InformationList-Rsp-Item

E-DCH-RL-InformationList-Rsp-Item ::= SEQUENCE {
	rl-ID								RL-ID,
	e-DCH-FDD-DL-Control-Channel-Info	E-DCH-FDD-DL-Control-Channel-Information,
	iE-Extensions									ProtocolExtensionContainer { { E-DCH-RL-InformationList-Rsp-Item-ExtIEs} }	OPTIONAL,
	...
}

E-DCH-serving-cell-change-successful-ExtIEs NBAP-PROTOCOL-EXTENSION ::= {
	...
}

E-DCH-RL-InformationList-Rsp-Item-ExtIEs NBAP-PROTOCOL-EXTENSION ::= {
	...
}

E-DCH-serving-cell-change-unsuccessful ::= SEQUENCE {
	cause							Cause,
	iE-Extensions					ProtocolExtensionContainer { { E-DCH-serving-cell-change-unsuccessful-ExtIEs} } OPTIONAL,
	...
}

E-DCH-serving-cell-change-unsuccessful-ExtIEs NBAP-PROTOCOL-EXTENSION ::= {
	...
}

-- The maximum repetitions should be limited to 1 so that this information is reported only once for a cell.
EDCH-RACH-Report-Value ::= SEQUENCE (SIZE(1.. maxNrOfCommonEDCH)) OF
	SEQUENCE {
		granted-EDCH-RACH-resources		Granted-EDCH-RACH-Resources-Value,
		denied-EDCH-RACH-resources		Denied-EDCH-RACH-Resources-Value,
		iE-Extensions		ProtocolExtensionContainer { { EDCH-RACH-Report-Value-ExtIEs } }	OPTIONAL,
		...
}

EDCH-RACH-Report-Value-ExtIEs NBAP-PROTOCOL-EXTENSION ::= {
	...
}

E-DCH-TFCI-Table-Index ::= INTEGER (0..1,...,2..7)

E-DCH-TTI-Length ::= CHOICE {
	two-ms		DTX-Cycle-2ms-Items,
	ten-ms		DTX-Cycle-10ms-Items,
	...
}

E-DCH-TTI-Length-to-Modify ::= CHOICE {
	two-ms		DTX-Cycle-2ms-to-Modify-Items,
	ten-ms		DTX-Cycle-10ms-to-Modify-Items,
	...
}


E-DPCCH-PO ::= INTEGER (0..maxNrOfEDPCCH-PO-QUANTSTEPs)

E-DPDCH-PowerInterpolation ::= BOOLEAN

E-Primary-Secondary-Grant-Selector ::= ENUMERATED {
	primary,
	secondary
}

E-DCH-MACdFlow-ID-LCR ::= INTEGER (0..maxNrOfEDCHMACdFlowsLCR-1)

E-DCH-MACdFlows-to-DeleteLCR ::= SEQUENCE (SIZE (1..maxNrOfEDCHMACdFlowsLCR)) OF E-DCH-MACdFlow-to-Delete-ItemLCR

E-DCH-MACdFlow-to-Delete-ItemLCR ::= SEQUENCE {
	e-DCH-MACdFlow-ID-LCR							E-DCH-MACdFlow-ID-LCR,
	iE-Extensions									ProtocolExtensionContainer { { E-DCH-MACdFlow-to-Delete-ItemLCR-ExtIEs} }					OPTIONAL,
	...
}

E-DCH-MACdFlow-to-Delete-ItemLCR-ExtIEs NBAP-PROTOCOL-EXTENSION ::= {
	...
}

Enhanced-UE-DRX-InformationLCR  ::= SEQUENCE {
	t321										T321,
	hS-DSCH-DRX-Cycle-FACH						HS-DSCH-DRX-Cycle-FACH,
	hS-DSCH-RX-Burst-FACH						HS-DSCH-RX-Burst-FACH,
	iE-Extensions								ProtocolExtensionContainer { { Enhanced-UE-DRX-InformationLCR-ExtIEs } }		OPTIONAL,
	...
}

Enhanced-UE-DRX-InformationLCR-ExtIEs NBAP-PROTOCOL-EXTENSION ::= {
	...
}

E-HICH-ID-LCR ::= INTEGER(0..255)
E-HICH-Signature-Sequence ::= INTEGER (0..maxNrofSigSeqRGHI-1)

End-Of-Audit-Sequence-Indicator ::= ENUMERATED {
	end-of-audit-sequence,
	not-end-of-audit-sequence
}

E-Serving-Grant-Value ::= INTEGER (0..38)

E-RGCH-2-IndexStepThreshold ::= INTEGER (0..37)

E-RGCH-3-IndexStepThreshold ::= INTEGER (0..37)

E-RGCH-E-HICH-FDD-Code-Information ::= CHOICE {
	replace					E-RGCH-E-HICH-FDD-Code-List,
	remove					NULL,
	...
}

E-RGCH-E-HICH-FDD-Code-List ::= SEQUENCE (SIZE (1..maxNrOfE-RGCHs-E-HICHs)) OF FDD-DL-ChannelisationCodeNumber

E-RGCH-Release-Indicator ::= ENUMERATED {e-RGCHreleased}

E-RGCH-Signature-Sequence ::= INTEGER (0..maxNrofSigSeqRGHI-1)

E-RNTI ::= INTEGER (0..65535)

E-TFCI ::= INTEGER (0..127)

E-TFCI-BetaEC-Boost ::= INTEGER (0..127,...)


E-TFCI-Boost-Information ::= SEQUENCE {
	e-TFCI-BetaEC-Boost								E-TFCI-BetaEC-Boost,
	uL-Delta-T2TP									UL-Delta-T2TP			OPTIONAL,
	-- This IE shall be present if the E-TFCI BetaEC Boost IE value is not set to 127.
	iE-Extensions									ProtocolExtensionContainer { { E-TFCI-Boost-Information-ExtIEs} }		OPTIONAL,
	...
}

E-TFCI-Boost-Information-ExtIEs NBAP-PROTOCOL-EXTENSION ::= {
	...
}

E-TFCS-Information ::= SEQUENCE {
	e-DCH-TFCI-Table-Index								E-DCH-TFCI-Table-Index,
	e-DCH-Min-Set-E-TFCI							E-TFCI			OPTIONAL,
	reference-E-TFCI-Information					Reference-E-TFCI-Information,
	iE-Extensions									ProtocolExtensionContainer { {E-TFCS-Information-ExtIEs} }		OPTIONAL,
	...
}

E-TFCS-Information-ExtIEs NBAP-PROTOCOL-EXTENSION ::= {
	{ ID id-E-TFCI-Boost-Information		CRITICALITY reject		EXTENSION	E-TFCI-Boost-Information		PRESENCE optional}|
	{ ID id-E-DPDCH-PowerInterpolation	CRITICALITY reject		EXTENSION	E-DPDCH-PowerInterpolation 	PRESENCE optional},
	...
}

E-TTI ::= ENUMERATED {
	e-TTI-2ms,
	e-TTI-10ms
}

E-DCHProvidedBitRate ::= SEQUENCE (SIZE (1..maxNrOfPriorityClasses)) OF E-DCHProvidedBitRate-Item

E-DCHProvidedBitRate-Item ::= SEQUENCE {
	schedulingPriorityIndicator			SchedulingPriorityIndicator,
	e-DCHProvidedBitRateValue			E-DCHProvidedBitRateValue,
	iE-Extensions						ProtocolExtensionContainer { { E-DCHProvidedBitRate-Item-ExtIEs} }		OPTIONAL,
	...
}

E-DCHProvidedBitRate-Item-ExtIEs NBAP-PROTOCOL-EXTENSION ::= {
	...
}

E-DCHProvidedBitRateValueInformation-For-CellPortion ::= SEQUENCE (SIZE (1..maxNrOfCellPortionsPerCellLCR)) OF E-DCHProvidedBitRateValueInformation-For-CellPortion-Item

E-DCHProvidedBitRateValueInformation-For-CellPortion-Item ::= SEQUENCE{
	cellPortionLCRID					CellPortionLCRID,
	e-DCHProvidedBitRateValue		E-DCHProvidedBitRate,
	iE-Extensions					ProtocolExtensionContainer { {E-DCHProvidedBitRateValueInformation-For-CellPortion-Item-ExtIEs} }	OPTIONAL,
	...
}

E-DCHProvidedBitRateValueInformation-For-CellPortion-Item-ExtIEs NBAP-PROTOCOL-EXTENSION ::= {
	...
}

E-AGCH-PowerOffset ::= INTEGER (0..255,...)
-- PowerOffset = -32 + offset * 0.25
-- Unit dB, Range -32dB .. +31.75dB, Step +0.25dB

E-RGCH-PowerOffset ::= INTEGER (0..255,...)
-- PowerOffset = -32 + offset * 0.25
-- Unit dB, Range -32dB .. +31.75dB, Step +0.25dB



E-HICH-PowerOffset ::= INTEGER (0..255,...)
-- PowerOffset = -32 + offset * 0.25
-- Unit dB, Range -32dB .. +31.75dB, Step +0.25dB

E-HICH-TimeOffset ::= INTEGER (4..44)

E-HICH-TimeOffsetLCR ::= INTEGER (4..15)


E-DCH-Information ::= SEQUENCE {
	e-PUCH-Information 							E-PUCH-Information,
	e-TFCS-Information-TDD 						E-TFCS-Information-TDD,
	e-DCH-MACdFlows-Information-TDD				E-DCH-MACdFlows-Information-TDD,
	e-DCH-Non-Scheduled-Grant-Info 				E-DCH-Non-Scheduled-Grant-Info	OPTIONAL,
	e-DCH-TDD-Information						E-DCH-TDD-Information,
	iE-Extensions								ProtocolExtensionContainer { { E-DCH-Information-ExtIEs} }		OPTIONAL,
	...
}

E-DCH-Information-ExtIEs NBAP-PROTOCOL-EXTENSION ::= {
	...
}

E-PUCH-Information  ::= SEQUENCE {
	minCR										CodeRate,
	maxCR										CodeRate,
	harqInfo									HARQ-Info-for-E-DCH,
	n-E-UCCH									N-E-UCCH,
	iE-Extensions								ProtocolExtensionContainer { { E-PUCH-Information-ExtIEs } }		OPTIONAL,
	...
}

E-PUCH-Information-ExtIEs NBAP-PROTOCOL-EXTENSION ::= {
	...
}

E-TFCS-Information-TDD  ::= SEQUENCE {
	e-DCH-QPSK-RefBetaInfo 						E-DCH-QPSK-RefBetaInfo,
	e-DCH-sixteenQAM-RefBetaInfo				E-DCH-sixteenQAM-RefBetaInfo,
	iE-Extensions								ProtocolExtensionContainer { { E-TFCS-Information-TDD-ExtIEs } }		OPTIONAL,
	...
}

E-TFCS-Information-TDD-ExtIEs NBAP-PROTOCOL-EXTENSION ::= {
	...
}

E-DCH-QPSK-RefBetaInfo ::= SEQUENCE (SIZE (1..maxNrOfRefBetas)) OF E-DCH-RefBeta-Item

E-DCH-sixteenQAM-RefBetaInfo ::= SEQUENCE (SIZE (1..maxNrOfRefBetas)) OF E-DCH-RefBeta-Item

E-DCH-RefBeta-Item  ::= SEQUENCE {
	refCodeRate				CodeRate-short,
	refBeta					RefBeta
}

E-DCH-MACdFlows-Information-TDD  ::= SEQUENCE (SIZE (1..maxNrOfEDCHMACdFlows)) OF E-DCH-MACdFlow-InfoTDDItem

E-DCH-MACdFlow-InfoTDDItem ::= SEQUENCE {
	e-DCH-MACdFlow-ID								E-DCH-MACdFlow-ID,
	allocationRetentionPriority						AllocationRetentionPriority,
	tnlQos											TnlQos						OPTIONAL,
	bindingID										BindingID					OPTIONAL,
	transportLayerAddress							TransportLayerAddress		OPTIONAL,
	payloadCRC-PresenceIndicator					PayloadCRC-PresenceIndicator,
	maximum-Number-of-Retransmissions-For-E-DCH		Maximum-Number-of-Retransmissions-For-E-DCH,
	eDCH-HARQ-PO-TDD								E-DCH-HARQ-PO-TDD,
	eDCH-MACdFlow-Multiplexing-List					E-DCH-MACdFlow-Multiplexing-List							OPTIONAL,
	eDCH-Grant-TypeTDD								E-DCH-Grant-TypeTDD,
	eDCHLogicalChannelInformation					E-DCH-LogicalChannelInformation,
	eDCH-MACdFlow-Retransmission-Timer				E-DCH-MACdFlow-Retransmission-Timer		OPTIONAL,
	-- Mandatory for LCR TDD,Not applicable for 3.84Mcps TDD and 7.68Mcps TDD
	iE-Extensions									ProtocolExtensionContainer { { E-DCH-MACdFlow-InfoTDDItem-ExtIEs} }				OPTIONAL,
	...
}

E-DCH-MACdFlow-InfoTDDItem-ExtIEs NBAP-PROTOCOL-EXTENSION ::= {
	...
}
E-DCH-MACdFlow-Retransmission-Timer ::= ENUMERATED {
	ms10, ms15, ms20, ms25, ms30, ms35, ms40, ms45, ms50, ms55, ms60, ms65,
	ms70, ms75, ms80, ms85, ms90, ms95, ms100, ms110, ms120, ms140, ms160,
	ms200, ms240, ms280, ms320, ms400, ms480, ms560,...
}


E-DCH-HARQ-PO-TDD ::= INTEGER (0..6)

E-DCH-Grant-TypeTDD ::= ENUMERATED {
	scheduled,
	non-scheduled
}
E-DCH-Non-Scheduled-Grant-Info  ::= SEQUENCE {
	timeslotResource							E-DCH-TimeslotResource,
	powerResource								E-DCH-PowerResource,
	repetitionPeriod							RepetitionPeriod,
	repetitionLength							RepetitionLength,
	tddE-PUCH-Offset							TddE-PUCH-Offset,
	tdd-ChannelisationCode						TDD-ChannelisationCode,
	iE-Extensions								ProtocolExtensionContainer { { E-DCH-Non-Scheduled-Grant-Info-ExtIEs } }		OPTIONAL,
	...
}

E-DCH-Non-Scheduled-Grant-Info-ExtIEs NBAP-PROTOCOL-EXTENSION ::= {
	...
}

E-DCH-TimeslotResource ::= BIT STRING (SIZE (13))

E-DCH-TimeslotResourceLCR ::= BIT STRING (SIZE (5))


E-DCH-PowerResource ::= INTEGER(1..32)

TddE-PUCH-Offset ::= INTEGER(0..255)

E-DCH-TDD-Information  ::= SEQUENCE {
	e-DCH-TDD-Maximum-Bitrate						E-DCH-TDD-Maximum-Bitrate							OPTIONAL,
	e-DCH-Processing-Overload-Level					E-DCH-Processing-Overload-Level						OPTIONAL,
	e-DCH-PowerOffset-for-SchedulingInfo			E-DCH-PowerOffset-for-SchedulingInfo				OPTIONAL,
	iE-Extensions									ProtocolExtensionContainer { { E-DCH-TDD-Information-ExtIEs } }		OPTIONAL,
	...
}

E-DCH-TDD-Information-ExtIEs NBAP-PROTOCOL-EXTENSION ::= {
	...
}

E-DCH-TDD-Maximum-Bitrate ::= INTEGER (0..9201,...)

E-DCH-Information-Response ::= SEQUENCE {
	e-DCH-TDD-MACdFlow-Specific-InformationResp		E-DCH-TDD-MACdFlow-Specific-InformationResp	OPTIONAL,
	e-AGCH-Specific-Information-ResponseTDD			E-AGCH-Specific-InformationRespListTDD	OPTIONAL,
	e-RNTI											E-RNTI,
	scheduled-E-HICH-Specific-InformationResp		Scheduled-E-HICH-Specific-Information-ResponseLCRTDD	OPTIONAL,	-- 1.28Mcps TDD only
	iE-Extensions									ProtocolExtensionContainer { { E-DCH-Information-Response-ExtIEs } }		OPTIONAL,
	...
}

E-DCH-Information-Response-ExtIEs NBAP-PROTOCOL-EXTENSION ::= {
	...
}

Scheduled-E-HICH-Specific-Information-ResponseLCRTDD ::= SEQUENCE (SIZE (1.. maxNrOfEHICHCodes)) OF Scheduled-E-HICH-Specific-InformationItem-ResponseLCRTDD

Scheduled-E-HICH-Specific-InformationItem-ResponseLCRTDD ::= SEQUENCE {
	eI								EI,
	e-HICH-ID-TDD					E-HICH-ID-TDD,
	iE-Extensions								ProtocolExtensionContainer  {{ Scheduled-E-HICH-Specific-InformationItem-ResponseLCRTDD-ExtIEs}}		OPTIONAL,
	...
}

Scheduled-E-HICH-Specific-InformationItem-ResponseLCRTDD-ExtIEs NBAP-PROTOCOL-EXTENSION ::= {
	{ ID id-Extended-E-HICH-ID-TDD	CRITICALITY ignore EXTENSION Extended-E-HICH-ID-TDD PRESENCE optional},
	-- Applicable to 1.28Mcps TDD only when the E-HICH identity has a value larger than 31.
	...
}

EI ::= INTEGER (0..3)

E-HICH-ID-TDD ::= INTEGER (0..31)

E-HICH-Type ::= ENUMERATED {scheduled,non-scheduled}

E-DCH-TDD-MACdFlow-Specific-InformationResp ::= SEQUENCE (SIZE (1..maxNrOfEDCHMACdFlows)) OF E-DCH-TDD-MACdFlow-Specific-InformationResp-Item

E-DCH-TDD-MACdFlow-Specific-InformationResp-Item ::= SEQUENCE {
	e-DCH-MacdFlow-Id								E-DCH-MACdFlow-ID,
	bindingID										BindingID					OPTIONAL,
	transportLayerAddress							TransportLayerAddress		OPTIONAL,
	iE-Extensions									ProtocolExtensionContainer { { E-DCH-TDD-MACdFlow-Specific-InformationRespItem-ExtIEs } }		OPTIONAL,
	...
}

E-DCH-TDD-MACdFlow-Specific-InformationRespItem-ExtIEs NBAP-PROTOCOL-EXTENSION ::= {
	...
}

E-AGCH-Specific-InformationRespListTDD ::= SEQUENCE (SIZE (1..maxNrOfEAGCHCodes)) OF E-AGCH-Specific-InformationResp-ItemTDD

E-AGCH-Specific-InformationResp-ItemTDD ::= SEQUENCE {
	e-AGCH-Id										E-AGCH-Id,
	iE-Extensions									ProtocolExtensionContainer { { E-AGCH-Specific-InformationResp-ItemTDD-ExtIEs } }		OPTIONAL,
	...
}

E-AGCH-Specific-InformationResp-ItemTDD-ExtIEs NBAP-PROTOCOL-EXTENSION ::= {
	...
}

E-AGCH-Id ::= INTEGER (0..31,...,32..255)

E-DCH-Information-Reconfig ::= SEQUENCE {
	e-PUCH-Information 							E-PUCH-Information									OPTIONAL,
	e-TFCS-Information-TDD 						E-TFCS-Information-TDD								OPTIONAL,
	e-DCH-MACdFlows-to-Add						E-DCH-MACdFlows-Information-TDD						OPTIONAL,
	e-DCH-MACdFlows-to-Delete					E-DCH-MACdFlows-to-Delete							OPTIONAL,
	e-DCH-Non-Scheduled-Grant-Info 				E-DCH-Non-Scheduled-Grant-Info						OPTIONAL,
	e-DCH-TDD-Information						E-DCH-TDD-Information								OPTIONAL,
	e-DCH-TDD-Information-to-Modify				E-DCH-TDD-Information-to-Modify						OPTIONAL,
	iE-Extensions								ProtocolExtensionContainer { { E-DCH-Information-Reconfig-ExtIEs} }	OPTIONAL,
	...
}

E-DCH-Information-Reconfig-ExtIEs NBAP-PROTOCOL-EXTENSION ::= {
	...
}

E-DCH-TDD-Information-to-Modify ::= SEQUENCE {
	e-DCH-TDD-Information-to-Modify-List	E-DCH-TDD-Information-to-Modify-List	OPTIONAL,
	mACeReset-Indicator						MACeReset-Indicator						OPTIONAL,
	iE-Extensions							ProtocolExtensionContainer { { E-DCH-TDD-Information-to-Modify-ExtIEs } }		OPTIONAL,
	...
}

E-DCH-TDD-Information-to-Modify-ExtIEs NBAP-PROTOCOL-EXTENSION ::= {
	{ ID id-E-DCH-MACdPDUSizeFormat 					CRITICALITY reject	EXTENSION	E-DCH-MACdPDUSizeFormat 					PRESENCE optional},
	...
}

E-DCH-TDD-Information-to-Modify-List ::= SEQUENCE (SIZE (1..maxNrOfEDCHMACdFlows)) OF E-DCH-MACdFlow-ModifyTDDItem

E-DCH-MACdFlow-ModifyTDDItem ::= SEQUENCE {
	e-DCH-MACdFlow-ID								E-DCH-MACdFlow-ID,
	allocationRetentionPriority						AllocationRetentionPriority		OPTIONAL,
	transportBearerRequestIndicator					TransportBearerRequestIndicator,
	bindingID										BindingID					OPTIONAL,
	transportLayerAddress							TransportLayerAddress		OPTIONAL,
	tnlQos											TnlQos						OPTIONAL,
	maximum-Number-of-Retransmissions-For-E-DCH		Maximum-Number-of-Retransmissions-For-E-DCH		OPTIONAL,
	eDCH-HARQ-PO-TDD								E-DCH-HARQ-PO-TDD										OPTIONAL,
	eDCH-MACdFlow-Multiplexing-List					E-DCH-MACdFlow-Multiplexing-List						OPTIONAL,
	eDCH-Grant-TypeTDD								E-DCH-Grant-TypeTDD										OPTIONAL,
	e-DCH-LogicalChannelToAdd						E-DCH-LogicalChannelInformation					OPTIONAL,
	e-DCH-LogicalChannelToModify					E-DCH-LogicalChannelToModify					OPTIONAL,
	e-DCH-LogicalChannelToDelete					E-DCH-LogicalChannelToDelete					OPTIONAL,
	eDCH-MACdFlow-Retransmission-Timer				E-DCH-MACdFlow-Retransmission-Timer				OPTIONAL,
	-- LCR TDD only
	iE-Extensions									ProtocolExtensionContainer { {E-DCH-MACdFlow-ModifyTDDItem-ExtIEs } }	OPTIONAL,
	...
}

E-DCH-MACdFlow-ModifyTDDItem-ExtIEs NBAP-PROTOCOL-EXTENSION ::= {
	...
}

Maximum-Generated-ReceivedTotalWideBandPowerInOtherCells ::= INTEGER (0..621)
-- mapping as for RTWP measurement value, as specified in [23]

E-DCH-768-Information ::= SEQUENCE {
	e-PUCH-Information 							E-PUCH-Information,
	e-TFCS-Information-TDD 						E-TFCS-Information-TDD,
	e-DCH-MACdFlows-Information-TDD				E-DCH-MACdFlows-Information-TDD,
	e-DCH-Non-Scheduled-Grant-Info768			E-DCH-Non-Scheduled-Grant-Info768	OPTIONAL,
	e-DCH-TDD-Information768					E-DCH-TDD-Information768,
	iE-Extensions								ProtocolExtensionContainer { { E-DCH-768-Information-ExtIEs} }		OPTIONAL,
	...
}

E-DCH-768-Information-ExtIEs NBAP-PROTOCOL-EXTENSION ::= {
	...
}

E-DCH-Non-Scheduled-Grant-Info768  ::= SEQUENCE {
	timeslotResource							E-DCH-TimeslotResource,
	powerResource								E-DCH-PowerResource,
	repetitionPeriod							RepetitionPeriod,
	repetitionLength							RepetitionLength,
	tddE-PUCH-Offset							TddE-PUCH-Offset,
	tdd-ChannelisationCode768					TDD-ChannelisationCode768,
	iE-Extensions								ProtocolExtensionContainer { { E-DCH-Non-Scheduled-Grant-Info768-ExtIEs } }		OPTIONAL,
	...
}

E-DCH-Non-Scheduled-Grant-Info768-ExtIEs NBAP-PROTOCOL-EXTENSION ::= {
	...
}

E-DCH-TDD-Information768  ::= SEQUENCE {
	e-DCH-TDD-Maximum-Bitrate768					E-DCH-TDD-Maximum-Bitrate768						OPTIONAL,
	e-DCH-Processing-Overload-Level					E-DCH-Processing-Overload-Level						OPTIONAL,
	e-DCH-PowerOffset-for-SchedulingInfo			E-DCH-PowerOffset-for-SchedulingInfo				OPTIONAL,
	iE-Extensions									ProtocolExtensionContainer { { E-DCH-TDD-Information768-ExtIEs } }		OPTIONAL,
	...
}

E-DCH-TDD-Information768-ExtIEs NBAP-PROTOCOL-EXTENSION ::= {
	...
}

E-DCH-TDD-Maximum-Bitrate768 ::= INTEGER (0..17713,...)

E-DCH-768-Information-Reconfig ::= SEQUENCE {
	e-PUCH-Information 							E-PUCH-Information									OPTIONAL,
	e-TFCS-Information-TDD 						E-TFCS-Information-TDD								OPTIONAL,
	e-DCH-MACdFlows-to-Add						E-DCH-MACdFlows-Information-TDD						OPTIONAL,
	e-DCH-MACdFlows-to-Delete					E-DCH-MACdFlows-to-Delete							OPTIONAL,
	e-DCH-Non-Scheduled-Grant-Info768			E-DCH-Non-Scheduled-Grant-Info768						OPTIONAL,
	e-DCH-TDD-Information768					E-DCH-TDD-Information768								OPTIONAL,
	e-DCH-TDD-Information-to-Modify				E-DCH-TDD-Information-to-Modify						OPTIONAL,
	iE-Extensions								ProtocolExtensionContainer { { E-DCH-768-Information-Reconfig-ExtIEs} }	OPTIONAL,
	...
}

E-DCH-768-Information-Reconfig-ExtIEs NBAP-PROTOCOL-EXTENSION ::= {
	...
}

E-DCH-LCR-Information ::= SEQUENCE {
	e-PUCH-LCR-Information 						E-PUCH-LCR-Information,
	e-TFCS-Information-TDD 						E-TFCS-Information-TDD,
	e-DCH-MACdFlows-Information-TDD				E-DCH-MACdFlows-Information-TDD,
	e-DCH-Non-Scheduled-Grant-LCR-Info			E-DCH-Non-Scheduled-Grant-LCR-Info	OPTIONAL,
	e-DCH-LCRTDD-Information					E-DCH-LCRTDD-Information,
	iE-Extensions								ProtocolExtensionContainer { { E-DCH-LCR-Information-ExtIEs} }		OPTIONAL,
	...
}

E-DCH-LCR-Information-ExtIEs NBAP-PROTOCOL-EXTENSION ::= {
	...
}

E-PUCH-LCR-Information ::= SEQUENCE {
	minCR										CodeRate,
	maxCR										CodeRate,
	harqInfo									HARQ-Info-for-E-DCH,
	pRXdes-base									PRXdes-base,
	e-PUCH-TPC-StepSize							TDD-TPC-UplinkStepSize-LCR,
	e-AGCH-TPC-StepSize							TDD-TPC-DownlinkStepSize,
	iE-Extensions								ProtocolExtensionContainer { { E-PUCH-LCR-Information-ExtIEs } }		OPTIONAL,
	...
}

E-PUCH-LCR-Information-ExtIEs NBAP-PROTOCOL-EXTENSION ::= {
	{ ID id-E-PUCH-PowerControlGAP		CRITICALITY ignore		EXTENSION ControlGAP		PRESENCE optional	},
	...
}

E-DCH-Non-Scheduled-Grant-LCR-Info ::= SEQUENCE {
	timeslotResourceLCR							E-DCH-TimeslotResourceLCR,
	powerResource								E-DCH-PowerResource,
	repetitionPeriod							RepetitionPeriod,
	repetitionLength							RepetitionLength,
	subframeNumber								ENUMERATED {v0, v1},
	tddE-PUCH-Offset							TddE-PUCH-Offset,
	tdd-ChannelisationCode						TDD-ChannelisationCode,
	n-E-UCCHLCR									N-E-UCCHLCR,
	e-HICH-LCR-Information						E-HICH-LCR-Information,
	iE-Extensions								ProtocolExtensionContainer { { E-DCH-Non-Scheduled-Grant-LCR-Info-ExtIEs } }		OPTIONAL,
	...
}

E-DCH-Non-Scheduled-Grant-LCR-Info-ExtIEs NBAP-PROTOCOL-EXTENSION ::= {
	...
}

E-HICH-LCR-Information	 ::= SEQUENCE {
	e-HICH-ID-TDD							E-HICH-ID-TDD,
	signatureSequenceGroupIndex					SignatureSequenceGroupIndex,
	iE-Extensions								ProtocolExtensionContainer { { E-HICH-LCR-Information-ExtIEs} }		OPTIONAL,
	...
}

E-HICH-LCR-Information-ExtIEs  NBAP-PROTOCOL-EXTENSION ::= {
	{ ID id-Extended-E-HICH-ID-TDD		CRITICALITY ignore	EXTENSION Extended-E-HICH-ID-TDD	PRESENCE optional},
	-- Applicable to 1.28Mcps TDD only when the E-HICH identity has a value larger than 31.
	...
}

E-DCH-LCRTDD-Information ::= SEQUENCE {
	e-DCH-LCRTDD-PhysicalLayerCategory			E-DCH-LCRTDD-PhysicalLayerCategory					OPTIONAL,
	e-DCH-Processing-Overload-Level				E-DCH-Processing-Overload-Level						OPTIONAL,
	e-DCH-PowerOffset-for-SchedulingInfo		E-DCH-PowerOffset-for-SchedulingInfo				OPTIONAL,
	iE-Extensions								ProtocolExtensionContainer { { E-DCH-LCRTDD-Information-ExtIEs } }		OPTIONAL,
	...
}

E-DCH-LCRTDD-Information-ExtIEs NBAP-PROTOCOL-EXTENSION ::= {
	{ ID id-Extended-E-DCH-LCRTDD-PhysicalLayerCategory						CRITICALITY reject		EXTENSION Extended-E-DCH-LCRTDD-PhysicalLayerCategory			PRESENCE optional }|
	-- This IE shall be used if the E-DCH Physical Layer Category has a value larger than 5.
	{ ID id-MaximumNumber-Of-Retransmission-for-Scheduling-Info-LCRTDD		CRITICALITY ignore		EXTENSION Maximum-Number-of-Retransmissions-For-E-DCH		PRESENCE optional }|
	{ ID id-E-DCH-RetransmissionTimer-for-SchedulingInfo-LCRTDD				CRITICALITY ignore		EXTENSION E-DCH-MACdFlow-Retransmission-Timer			PRESENCE optional }|
	{ ID id-E-AGCH-UE-Inactivity-Monitor-Threshold							CRITICALITY ignore		EXTENSION E-AGCH-UE-Inactivity-Monitor-Threshold			PRESENCE optional },
	...
}

E-DCH-LCRTDD-PhysicalLayerCategory ::= INTEGER(1..5)

E-DCH-LCR-Information-Reconfig ::= SEQUENCE {
	e-PUCH-LCR-Information 						E-PUCH-LCR-Information								OPTIONAL,
	e-TFCS-Information-TDD 						E-TFCS-Information-TDD								OPTIONAL,
	e-DCH-MACdFlows-to-Add						E-DCH-MACdFlows-Information-TDD						OPTIONAL,
	e-DCH-MACdFlows-to-Delete					E-DCH-MACdFlows-to-Delete							OPTIONAL,
	e-DCH-Non-Scheduled-Grant-LCR-Info			E-DCH-Non-Scheduled-Grant-LCR-Info					OPTIONAL,
	e-DCH-LCRTDD-Information					E-DCH-LCRTDD-Information							OPTIONAL,
	e-DCH-TDD-Information-to-Modify				E-DCH-TDD-Information-to-Modify						OPTIONAL,
	iE-Extensions								ProtocolExtensionContainer { { E-DCH-LCR-Information-Reconfig-ExtIEs} }	OPTIONAL,
	...
}

E-DCH-LCR-Information-Reconfig-ExtIEs NBAP-PROTOCOL-EXTENSION ::= {
	...
}


Enabling-Delay ::= ENUMERATED {v0, v1, v2, v4, v8, v16, v32, v64, v128}
	-- Unit of radio frames

DormantModeIndicator::= ENUMERATED {
	enterDormantMode,
	leaveDormantMode,
...
}

Enhanced-FACH-Capability ::= ENUMERATED {
	enhanced-FACH-capable,
	enhanced-FACH-non-capable
}

EnhancedHSServingCC-Abort ::= ENUMERATED {abortEnhancedHSServingCC,...}

Enhanced-PCH-Capability ::= ENUMERATED {
	enhanced-PCH-capable,
	enhanced-PCH-non-capable
}


Enhanced-UE-DRX-Capability ::= ENUMERATED {
	enhanced-UE-DRX-capable,
	enhanced-UE-DRX-non-capable
}

Enhanced-UE-DRX-InformationFDD  ::= SEQUENCE {
	t321										T321,
	hS-DSCH-DRX-Cycle-FACH						HS-DSCH-DRX-Cycle-FACH,
	hS-DSCH-RX-Burst-FACH						HS-DSCH-RX-Burst-FACH,
	dRX-Interruption-by-HS-DSCH					DRX-Interruption-by-HS-DSCH,
	iE-Extensions									ProtocolExtensionContainer { { Enhanced-UE-DRX-InformationFDD-ExtIEs } }		OPTIONAL,
	...
}

Enhanced-UE-DRX-InformationFDD-ExtIEs NBAP-PROTOCOL-EXTENSION ::= {
	...
}

Extended-E-DCH-LCRTDD-PhysicalLayerCategory ::= INTEGER(6,...)

Ext-Max-Bits-MACe-PDU-non-scheduled ::= INTEGER(19983..22978,...)

Ext-Reference-E-TFCI-PO ::= INTEGER(30..31,...)

ExtendedPropagationDelay ::= INTEGER(255..1023)

Extended-RNC-ID					::= INTEGER (4096..65535)

Extended-Round-Trip-Time-Value ::= INTEGER(32767..103041)
-- See also mapping in [22]

Extended-HS-SCCH-ID					::= INTEGER (32..255)

Extended-HS-SICH-ID					::= INTEGER (32..255)

Extended-E-HICH-ID-TDD				::= INTEGER (32..255)

E-DCH-Semi-PersistentScheduling-Information-LCR ::= SEQUENCE {
	repetition-Period-List-LCR				Repetition-Period-List-LCR,
	e-DCH-SPS-Indicator						E-DCH-SPS-Indicator,
	sPS-E-DCH-releted-E-HICH-Information	E-HICH-LCR-Information,
	iE-Extensions							ProtocolExtensionContainer { { E-DCH-Semi-PersistentScheduling-Information-LCR-ExtIEs } }			OPTIONAL,
	...
}

E-DCH-Semi-PersistentScheduling-Information-LCR-ExtIEs NBAP-PROTOCOL-EXTENSION ::= {
{ ID id-E-DCH-SPS-Reservation-Indicator		CRITICALITY ignore		EXTENSION SPS-Reservation-Indicator	PRESENCE optional },
	...
}

E-DCH-SPS-Indicator ::= BIT STRING (SIZE (16))

E-DCH-Semi-PersistentScheduling-Information-to-Modify-LCR ::= SEQUENCE {
	repetition-Period-List-LCR				Repetition-Period-List-LCR		OPTIONAL,
	e-DCH-SPS-Indicator						E-DCH-SPS-Indicator				OPTIONAL,
	sPS-E-DCH-releted-E-HICH-Information	E-HICH-LCR-Information			OPTIONAL,
	iE-Extensions							ProtocolExtensionContainer { { E-DCH-Semi-PersistentScheduling-Information-to-Modify-LCR-ExtIEs } }			OPTIONAL,
	...
}

E-DCH-Semi-PersistentScheduling-Information-to-Modify-LCR-ExtIEs NBAP-PROTOCOL-EXTENSION ::= {
{ ID id-E-DCH-SPS-Reservation-Indicator		CRITICALITY ignore		EXTENSION SPS-Reservation-Indicator	PRESENCE optional },
	...
}

E-DCH-Semi-PersistentScheduling-Information-ResponseLCR ::= SEQUENCE {
	timeslot-Resource-Related-Information		E-DCH-TimeslotResourceLCR,
	powerResource								E-DCH-PowerResource,
	repetition-Period-List-LCR					Repetition-Period-List-LCR,
	-- the IE shall be ignored
	repetitionLength							RepetitionLength,
	-- the IE shall be ignored
	subframeNumber								ENUMERATED {v0, v1},
	tddE-PUCH-Offset							TddE-PUCH-Offset,
	tdd-ChannelisationCode						TDD-ChannelisationCode,
	n-E-UCCHLCR									N-E-UCCHLCR,
	iE-Extensions								ProtocolExtensionContainer { { E-DCH-Semi-PersistentScheduling-Information-ResponseLCR-ExtIEs } }			OPTIONAL,
	...
}

E-DCH-Semi-PersistentScheduling-Information-ResponseLCR-ExtIEs NBAP-PROTOCOL-EXTENSION ::= {
	{ ID id-RepetitionPeriodIndex	CRITICALITY reject	EXTENSION RepetitionPeriodIndex		PRESENCE	optional },
	-- mandaroty for 1.28Mcps TDD.
	...
}

-- ==========================================
--	F
-- ==========================================

FACH-Measurement-Occasion-Cycle-Length-Coefficient ::= INTEGER(1..12)

Fast-Reconfiguration-Mode ::= ENUMERATED {fast,...}
Fast-Reconfiguration-Permission ::= ENUMERATED {allowed,...}

FDD-DL-ChannelisationCodeNumber ::= INTEGER(0.. 511)
-- According to the mapping in [9]. The maximum value is equal to the DL spreading factor -1--

FDD-DL-CodeInformation ::= SEQUENCE (SIZE (1..maxNrOfCodes)) OF FDD-DL-CodeInformationItem

FDD-DL-CodeInformationItem ::= SEQUENCE {
	dl-ScramblingCode						DL-ScramblingCode,
	fdd-DL-ChannelisationCodeNumber			FDD-DL-ChannelisationCodeNumber,
	transmissionGapPatternSequenceCodeInformation		TransmissionGapPatternSequenceCodeInformation		OPTIONAL,
	iE-Extensions							ProtocolExtensionContainer { { FDD-DL-CodeInformationItem-ExtIEs} }	OPTIONAL,
	...
}

FDD-DL-CodeInformationItem-ExtIEs NBAP-PROTOCOL-EXTENSION ::= {
	...
}

FDD-S-CCPCH-FrameOffset ::= ENUMERATED {
	v1, v2, v4, ...
}

FDD-S-CCPCH-Offset ::= INTEGER (0..149)
-- 0: 0 chip, 1: 256 chip, 2: 512 chip, .. ,149: 38144 chip [7] --

FDD-TPC-DownlinkStepSize ::= ENUMERATED {
	step-size0-5,
	step-size1,
	step-size1-5,
	step-size2,
	...
}

F-DPCH-Capability ::= ENUMERATED {
	f-DPCH-capable,
	f-DPCH-non-capable
}

F-DPCH-SlotFormat ::= INTEGER (0..9)


F-DPCH-SlotFormatCapability ::= ENUMERATED {
	f-DPCH-slot-format-capable,
	f-DPCH-slot-format-non-capable
}

FirstRLS-Indicator ::= ENUMERATED {
	first-RLS,
	not-first-RLS,
	...
}

FNReportingIndicator ::= ENUMERATED {
 fN-reporting-required,
 fN-reporting-not-required
}

FrameHandlingPriority ::= INTEGER (0..15)
-- 0=lowest priority, 15=highest priority --

FrameAdjustmentValue ::= INTEGER(0..4095)

FrameOffset ::= INTEGER (0..255)

FPACH-Power ::= INTEGER (-150..400,...) -- FPACH-power = power * 10
-- If power <= -15 FPACH shall be set to -150
-- If power >= 40 FPACH shall be set to 400
-- Unit dBm, Range -15dBm .. +40 dBm, Step +0.1dB

-- ==========================================
--	G
-- ==========================================


GANSS-AddClockModels ::= CHOICE {
	navClockModel			 		GANSS-NAVclockModel,
	cnavClockModel			 		GANSS-CNAVclockModel,
	glonassClockModel		 		GANSS-GLONASSclockModel,
	sbasClockModel			 		GANSS-SBASclockModel,
	...
}

GANSS-AddIonoModelReq ::= BIT STRING (SIZE(2))

GANSS-AddNavigationModelsReq ::= BOOLEAN

GANSS-AddOrbitModels ::= CHOICE {
	navKeplerianSet	 				GANSS-NavModel-NAVKeplerianSet,
	cnavKeplerianSet				GANSS-NavModel-CNAVKeplerianSet,
	glonassECEF						GANSS-NavModel-GLONASSecef,
	sbasECEF						GANSS-NavModel-SBASecef,
	...
	}

GANSS-AddUTCModelsReq ::= BOOLEAN

GANSS-Additional-Ionospheric-Model ::= SEQUENCE {
	dataID								BIT STRING (SIZE(2)),
	alpha-beta-parameters				GPS-Ionospheric-Model,
	ie-Extensions						ProtocolExtensionContainer { { GANSS-Additional-Ionospheric-Model-ExtIEs } }	OPTIONAL,
	...
}

GANSS-Additional-Ionospheric-Model-ExtIEs NBAP-PROTOCOL-EXTENSION ::= {
	...
}

GANSS-Additional-Navigation-Models ::= SEQUENCE {
	ganss-Transmission-Time		GANSS-Transmission-Time,
	non-broadcastIndication		ENUMERATED { true }																	OPTIONAL,
	ganssSatInfoNavList			Ganss-Sat-Info-AddNavList,
	ie-Extensions				ProtocolExtensionContainer { { GANSS-Additional-Navigation-Models-ExtIEs } } OPTIONAL,
	...
}

GANSS-Additional-Navigation-Models-ExtIEs NBAP-PROTOCOL-EXTENSION ::= {
	...
}

GANSS-Additional-Time-Models ::= SEQUENCE (SIZE (1..maxGANSS-1)) OF GANSS-Time-Model

GANSS-Additional-UTC-Models ::= CHOICE {
	utcModel1			GANSS-UTCmodelSet1,
	utcModel2			GANSS-UTCmodelSet2,
	utcModel3			GANSS-UTCmodelSet3,
	...
}

GANSS-Almanac ::= SEQUENCE{
	ganss-wk-number						INTEGER(0..255),
	gANSS-AlmanacModel					GANSS-AlmanacModel,
	ie-Extensions		 				ProtocolExtensionContainer { { GANSS-Almanac-ExtIEs } }		OPTIONAL,
	...
}

GANSS-Almanac-ExtIEs NBAP-PROTOCOL-EXTENSION ::= {
	...
}

GANSS-AlmanacModel ::= CHOICE {
	gANSS-keplerianParameters			GANSS-KeplerianParametersAlm,
	...,
	extension-GANSS-AlmanacModel		Extension-GANSS-AlmanacModel
}

Extension-GANSS-AlmanacModel	::= ProtocolIE-Single-Container {{ Extension-GANSS-AlmanacModel-IE }}

Extension-GANSS-AlmanacModel-IE NBAP-PROTOCOL-IES ::= {
	{ ID id-GANSS-alm-keplerianNAVAlmanac			CRITICALITY		ignore		TYPE	GANSS-ALM-NAVKeplerianSet			PRESENCE	mandatory}|
	{ ID id-GANSS-alm-keplerianReducedAlmanac		CRITICALITY		ignore		TYPE	GANSS-ALM-ReducedKeplerianSet		PRESENCE	mandatory}|
	{ ID id-GANSS-alm-keplerianMidiAlmanac			CRITICALITY		ignore		TYPE	GANSS-ALM-MidiAlmanacSet				PRESENCE	mandatory}|
	{ ID id-GANSS-alm-keplerianGLONASS				CRITICALITY		ignore		TYPE	GANSS-ALM-GlonassAlmanacSet			PRESENCE	mandatory}|
	{ ID id-GANSS-alm-ecefSBASAlmanac				CRITICALITY		ignore		TYPE	GANSS-ALM-ECEFsbasAlmanacSet		PRESENCE	mandatory}
}

GANSS-ALM-ECEFsbasAlmanacSet ::= SEQUENCE {
	sat-info-SBASecefList		GANSS-SAT-Info-Almanac-SBASecefList,
	ie-Extensions		 		ProtocolExtensionContainer { { GANSS-ALM-ECEFsbasAlmanacSet-ExtIEs } }		OPTIONAL,
	...
}

GANSS-ALM-ECEFsbasAlmanacSet-ExtIEs NBAP-PROTOCOL-EXTENSION ::= {
	...
}

GANSS-ALM-GlonassAlmanacSet ::= SEQUENCE {
	sat-info-GLOkpList			GANSS-SAT-Info-Almanac-GLOkpList,
	ie-Extensions		 		ProtocolExtensionContainer { { GANSS-ALM-GlonassAlmanacSet-ExtIEs } }		OPTIONAL,
	...
}

GANSS-ALM-GlonassAlmanacSet-ExtIEs NBAP-PROTOCOL-EXTENSION ::= {
	...
}

GANSS-ALM-MidiAlmanacSet ::= SEQUENCE {
	t-oa						INTEGER (0..255),
	sat-info-MIDIkpList			GANSS-SAT-Info-Almanac-MIDIkpList,
	ie-Extensions		 		ProtocolExtensionContainer { { GANSS-ALM-MidiAlmanacSet-ExtIEs } }		OPTIONAL,
	...
}

GANSS-ALM-MidiAlmanacSet-ExtIEs NBAP-PROTOCOL-EXTENSION ::= {
	...
}

GANSS-ALM-NAVKeplerianSet ::= SEQUENCE {
	t-oa						INTEGER (0..255),
	sat-info-NAVkpList			GANSS-SAT-Info-Almanac-NAVkpList,
	ie-Extensions		 		ProtocolExtensionContainer { { GANSS-ALM-NAVKeplerianSet-ExtIEs } }		OPTIONAL,
	...
}

GANSS-ALM-NAVKeplerianSet-ExtIEs NBAP-PROTOCOL-EXTENSION ::= {
	...
}

GANSS-ALM-ReducedKeplerianSet ::= SEQUENCE {
	t-oa						INTEGER (0..255),
	sat-info-REDkpList			GANSS-SAT-Info-Almanac-REDkpList,
	ie-Extensions		 		ProtocolExtensionContainer { { GANSS-ALM-ReducedKeplerianSet-ExtIEs } }		OPTIONAL,
	...
}

GANSS-ALM-ReducedKeplerianSet-ExtIEs NBAP-PROTOCOL-EXTENSION ::= {
	...
}

GANSS-Auxiliary-Information ::= CHOICE {
	ganssID1	GANSS-AuxInfoGANSS-ID1, 	-- This choice may only be present if GANSS ID indicates Modernized GPS
	ganssID3	GANSS-AuxInfoGANSS-ID3, 	-- This choice may only be present if GANSS ID indicates GLONASS
	...
}

GANSS-AuxInfoGANSS-ID1 ::= SEQUENCE (SIZE(1.. maxGANSSSat)) OF GANSS-AuxInfoGANSS-ID1-element

GANSS-AuxInfoGANSS-ID1-element ::= SEQUENCE {
	svID				INTEGER(0..63),
	signalsAvailable	BIT STRING (SIZE(8)),
	ie-Extensions		ProtocolExtensionContainer { { GANSS-AuxInfoGANSS-ID1-element-ExtIEs } }	OPTIONAL,
	...
}

GANSS-AuxInfoGANSS-ID1-element-ExtIEs NBAP-PROTOCOL-EXTENSION ::= {
	...
}

GANSS-AuxInfoGANSS-ID3 ::= SEQUENCE (SIZE(1.. maxGANSSSat)) OF GANSS-AuxInfoGANSS-ID3-element

GANSS-AuxInfoGANSS-ID3-element  ::= SEQUENCE {
	svID				INTEGER(0..63),
	signalsAvailable	BIT STRING (SIZE(8)),
	channelNumber		INTEGER (-7..13),
	ie-Extensions		ProtocolExtensionContainer { { GANSS-AuxInfoGANSS-ID3-element-ExtIEs } }	OPTIONAL,
	...
}

GANSS-AuxInfoGANSS-ID3-element-ExtIEs NBAP-PROTOCOL-EXTENSION ::= {
	...
}

GANSS-AuxInfoReq ::= BOOLEAN

GANSS-Clock-Model ::= SEQUENCE (SIZE (1..maxGANSSClockMod)) OF GANSS-SatelliteClockModelItem

GANSS-CNAVclockModel ::= SEQUENCE {
	cnavToc				BIT STRING (SIZE (11)),
	cnavTop				BIT STRING (SIZE (11)),
	cnavURA0			BIT STRING (SIZE (5)),
	cnavURA1			BIT STRING (SIZE (3)),
	cnavURA2			BIT STRING (SIZE (3)),
	cnavAf2				BIT STRING (SIZE (10)),
	cnavAf1				BIT STRING (SIZE (20)),
	cnavAf0				BIT STRING (SIZE (26)),
	cnavTgd				BIT STRING (SIZE (13)),
	cnavISCl1cp			BIT STRING (SIZE (13)) 											OPTIONAL,
	cnavISCl1cd			BIT STRING (SIZE (13))											OPTIONAL,
	cnavISCl1ca			BIT STRING (SIZE (13))											OPTIONAL,
	cnavISCl2c			BIT STRING (SIZE (13))											OPTIONAL,
	cnavISCl5i5			BIT STRING (SIZE (13)) 											OPTIONAL,
	cnavISCl5q5			BIT STRING (SIZE (13))											OPTIONAL,
	ie-Extensions		ProtocolExtensionContainer { { GANSS-CNAVclockModel-ExtIEs } }	OPTIONAL,
	...
}

GANSS-CNAVclockModel-ExtIEs NBAP-PROTOCOL-EXTENSION ::= {
	...
}

GANSS-Common-Data ::= SEQUENCE {
	ganss-Ionospheric-Model				GANSS-Ionospheric-Model																OPTIONAL,
	ganss-Rx-Pos						GANSS-RX-Pos																		OPTIONAL,
	ie-Extensions						ProtocolExtensionContainer { { GANSS-Common-Data-ExtIEs } }	OPTIONAL,
	...
}

GANSS-Common-Data-ExtIEs NBAP-PROTOCOL-EXTENSION ::= {
	{ ID id-GANSS-Additional-Ionospheric-Model		CRITICALITY ignore	EXTENSION GANSS-Additional-Ionospheric-Model	PRESENCE optional }|
	{ ID id-GANSS-Earth-Orientation-Parameters		CRITICALITY ignore	EXTENSION GANSS-Earth-Orientation-Parameters	PRESENCE optional },
	...
}

GANSS-CommonDataInfoReq ::= SEQUENCE {
	ionospheric-Model					BOOLEAN																				OPTIONAL,
	ie-Extensions						ProtocolExtensionContainer { { GANSS-CommonDataInfoReq-ExtIEs } }	OPTIONAL,
	...
}

GANSS-CommonDataInfoReq-ExtIEs NBAP-PROTOCOL-EXTENSION ::= {
	{ID id-GANSS-AddIonoModelReq		CRITICALITY	ignore	EXTENSION	GANSS-AddIonoModelReq									PRESENCE	optional} |
	{ID id-GANSS-EarthOrientParaReq		CRITICALITY	ignore	EXTENSION	GANSS-EarthOrientParaReq		PRESENCE	optional} ,
	...
}

GANSS-Data-Bit-Assistance ::= SEQUENCE {
	ganssTod							INTEGER (0..59,...),
	dataBitAssistancelist				GANSS-DataBitAssistanceList,
	ie-Extensions						ProtocolExtensionContainer { { GANSS-Data-Bit-Assistance-ExtIEs } }	OPTIONAL,
	...
}

GANSS-Data-Bit-Assistance-ExtIEs NBAP-PROTOCOL-EXTENSION ::= {
	...
}

GANSS-DataBitAssistanceList ::= SEQUENCE (SIZE (1..maxGANSSSat)) OF GANSS-DataBitAssistanceItem

GANSS-DataBitAssistanceItem ::= SEQUENCE {
	satId							INTEGER(0..63),
	dataBitAssistanceSgnList		GANSS-DataBitAssistanceSgnList,
	ie-Extensions					ProtocolExtensionContainer { { GANSS-DataBitAssistanceItem-ExtIEs } }	OPTIONAL,
	...
}

GANSS-DataBitAssistanceItem-ExtIEs NBAP-PROTOCOL-EXTENSION ::= {
	...
}

GANSS-DataBitAssistanceSgnList ::= SEQUENCE (SIZE (1..maxSgnType)) OF GANSS-DataBitAssistanceSgnItem



GANSS-DataBitAssistanceSgnItem ::= SEQUENCE {
	ganss-SignalId			GANSS-Signal-ID,
	ganssDataBits			BIT STRING (SIZE (1..1024)),
	ie-Extensions			ProtocolExtensionContainer { { GANSS-DataBitAssistanceSgnItem-ExtIEs } }	OPTIONAL,
	...
}

GANSS-DataBitAssistanceSgnItem-ExtIEs NBAP-PROTOCOL-EXTENSION ::= {
	...
}

GANSS-Data-Bit-Assistance-ReqItem ::= SEQUENCE {
	ganssTod								INTEGER (0..86399),
	ganss-Data-Bit-Assistance-ReqList		GANSS-Data-Bit-Assistance-ReqList,
	iE-Extensions							ProtocolExtensionContainer { { GANSS-Data-Bit-Assistance-ReqItem-ExtIEs } }	OPTIONAL,
	...
}

GANSS-Data-Bit-Assistance-ReqItem-ExtIEs NBAP-PROTOCOL-EXTENSION ::= {
	...
}

GANSS-Data-Bit-Assistance-ReqList ::= SEQUENCE {
	dGANSS-Signal-ID					BIT STRING (SIZE (8)),
	ganss-DataBitInterval				INTEGER(0..15),
	ganss-SatelliteInfo					SEQUENCE (SIZE (1..maxGANSSSat)) OF INTEGER(0..63) 											OPTIONAL,
	iE-Extensions						ProtocolExtensionContainer { { GANSS-Data-Bit-Assistance-ReqList-ExtIEs } }			OPTIONAL,
	...
}

GANSS-Data-Bit-Assistance-ReqList-ExtIEs NBAP-PROTOCOL-EXTENSION ::= {
	...
}


GANSS-DeltaUT1 ::= SEQUENCE {
	b1					BIT STRING (SIZE(11)),
	b2					BIT STRING (SIZE(10)),
	ie-Extensions		ProtocolExtensionContainer { { GANSS-DeltaUT1-ExtIEs } }	OPTIONAL,
	...
}

GANSS-DeltaUT1-ExtIEs NBAP-PROTOCOL-EXTENSION ::= {
	...
}

GANSS-Earth-Orientation-Parameters ::= SEQUENCE {
	teop				BIT STRING (SIZE (16)),
	pmX					BIT STRING (SIZE (21)),
	pmXdot				BIT STRING (SIZE (15)),
	pmY					BIT STRING (SIZE (21)),
	pmYdot				BIT STRING (SIZE (15)),
	deltaUT1			BIT STRING (SIZE (31)),
	deltaUT1dot			BIT STRING (SIZE (19)),
	ie-Extensions		ProtocolExtensionContainer { { GANSS-Earth-Orientation-Parameters-ExtIEs } }	OPTIONAL,
	...
}

GANSS-Earth-Orientation-Parameters-ExtIEs NBAP-PROTOCOL-EXTENSION ::= {
	...
}

GANSS-EarthOrientParaReq ::= BOOLEAN

GANSS-GenericDataInfoReqList ::= SEQUENCE (SIZE(1..maxNoGANSS)) OF GANSS-GenericDataInfoReqItem

GANSS-GenericDataInfoReqItem ::= SEQUENCE {
	ganss-Id									GANSS-ID																			OPTIONAL,
	ganss-Navigation-Model-And-Time-Recovery	BOOLEAN															OPTIONAL,
	ganss-Time-Model-GNSS-GNSS					BIT STRING (SIZE (9))											OPTIONAL,
	ganss-UTC-Model								BOOLEAN															OPTIONAL,
	ganss-Almanac								BOOLEAN															OPTIONAL,
	ganss-Real-Time-Integrity					BOOLEAN															OPTIONAL,
	ganss-Data-Bit-Assistance-Req				GANSS-Data-Bit-Assistance-ReqItem								OPTIONAL,
	ie-Extensions								ProtocolExtensionContainer { { GANSS-GenericDataInfoReqItem-ExtIEs } }		OPTIONAL,
	...
}

GANSS-GenericDataInfoReqItem-ExtIEs NBAP-PROTOCOL-EXTENSION ::= {
	{ID id-GANSS-AddNavigationModelsReq	CRITICALITY	ignore	EXTENSION	GANSS-AddNavigationModelsReq						PRESENCE	optional} |
	{ID id-GANSS-AddUTCModelsReq		CRITICALITY	ignore	EXTENSION	GANSS-AddUTCModelsReq								PRESENCE	optional} |
	{ID id-GANSS-AuxInfoReq				CRITICALITY	ignore	EXTENSION	GANSS-AuxInfoReq									PRESENCE	optional} |
-- The following IE shall be present if 'GANSS-ID' in 'GANSS-GenericDataInfoReqItem' is '0' (SBAS)
	{ID id-GANSS-SBAS-ID				CRITICALITY	ignore	EXTENSION	GANSS-SBAS-ID				PRESENCE	optional} ,
	...
}

GANSS-Generic-Data ::= SEQUENCE (SIZE(1..maxNoGANSS)) OF GANSS-Generic-DataItem

GANSS-Generic-DataItem ::= SEQUENCE {
	ganss-Id									GANSS-ID																			OPTIONAL,
	dganss-Correction							DGANSSCorrections																	OPTIONAL,
	ganss-Navigation-Model-And-Time-Recovery	GANSS-Navigation-Model-And-Time-Recovery											OPTIONAL,
	ganss-Time-Model							GANSS-Time-Model																	OPTIONAL,
	ganss-UTC-TIME								GANSS-UTC-Model																		OPTIONAL,
	ganss-Almanac								GANSS-Almanac																		OPTIONAL,
	ganss-Real-Time-Integrity					GANSS-Real-Time-Integrity															OPTIONAL,
	ganss-Data-Bit-Assistance					GANSS-Data-Bit-Assistance															OPTIONAL,
	ie-Extensions								ProtocolExtensionContainer { { GANSS-Generic-DataItem-ExtIEs } }			OPTIONAL,
	...
}

GANSS-Generic-DataItem-ExtIEs NBAP-PROTOCOL-EXTENSION ::= {
	{ ID id-GANSS-Additional-Time-Models			CRITICALITY ignore	EXTENSION GANSS-Additional-Time-Models			PRESENCE optional }|
	{ ID id-GANSS-Additional-Navigation-Models		CRITICALITY ignore	EXTENSION GANSS-Additional-Navigation-Models	PRESENCE optional }|
	{ ID id-GANSS-Additional-UTC-Models				CRITICALITY ignore	EXTENSION GANSS-Additional-UTC-Models				PRESENCE optional }|
	{ ID id-GANSS-Auxiliary-Information				CRITICALITY ignore	EXTENSION GANSS-Auxiliary-Information				PRESENCE optional }|
	-- The following element shall be present if 'GANSS-ID' in 'GANSS-Generic-DataItem' is '0' ('SBAS')
	{ ID id-GANSS-SBAS-ID							CRITICALITY ignore	EXTENSION GANSS-SBAS-ID			PRESENCE optional },
	...
}


GANSS-GLONASSclockModel ::= SEQUENCE {
	gloTau					BIT STRING (SIZE (22)),
	gloGamma				BIT STRING (SIZE (11)),
	gloDeltaTau				BIT STRING (SIZE (5)) 												OPTIONAL,
	ie-Extensions			ProtocolExtensionContainer { { GANSS-GLONASSclockModel-ExtIEs } }	OPTIONAL,
	...
}

GANSS-GLONASSclockModel-ExtIEs NBAP-PROTOCOL-EXTENSION ::= {
	...
}

GANSS-ID ::= INTEGER(0..7,...)


GANSS-Information ::= SEQUENCE {
	gANSS-CommonDataInfoReq				GANSS-CommonDataInfoReq											OPTIONAL,
	gANSS-GenericDataInfoReqList		GANSS-GenericDataInfoReqList									OPTIONAL,
	ie-Extensions						ProtocolExtensionContainer { { GANSS-Information-ExtIEs } }	OPTIONAL,
	...
}

GANSS-Information-ExtIEs NBAP-PROTOCOL-EXTENSION ::= {
	...
}

GANSS-Ionospheric-Model ::= SEQUENCE {
	alpha-zero-ionos					BIT STRING (SIZE (12)),
	alpha-one-ionos						BIT STRING (SIZE (12)),
	alpha-two-ionos						BIT STRING (SIZE (12)),
	gANSS-IonosphereRegionalStormFlags	GANSS-IonosphereRegionalStormFlags							OPTIONAL,
	ie-Extensions						ProtocolExtensionContainer { { GANSS-Ionospheric-Model-ExtIEs } }	OPTIONAL,
	...
}

GANSS-Ionospheric-Model-ExtIEs NBAP-PROTOCOL-EXTENSION ::= {
	...
}

GANSS-IonosphereRegionalStormFlags ::= SEQUENCE {
	storm-flag-one						BOOLEAN,
	storm-flag-two						BOOLEAN,
	storm-flag-three					BOOLEAN,
	storm-flag-four						BOOLEAN,
	storm-flag-five						BOOLEAN,
	ie-Extensions						ProtocolExtensionContainer { { GANSS-IonosphereRegionalStormFlags-ExtIEs } } OPTIONAL,
	...
}

GANSS-IonosphereRegionalStormFlags-ExtIEs NBAP-PROTOCOL-EXTENSION ::= {
	...
}

GANSS-KeplerianParametersAlm ::= SEQUENCE {
	t-oa								INTEGER(0..255),
	iod-a								INTEGER(0..3),
	gANSS-SatelliteInformationKP		GANSS-SatelliteInformationKP,
	ie-Extensions		 				ProtocolExtensionContainer { { GANSS-KeplerianParametersAlm-ExtIEs } }		OPTIONAL,
	...
}

GANSS-KeplerianParametersAlm-ExtIEs NBAP-PROTOCOL-EXTENSION ::= {
	...
}

GANSS-KeplerianParametersOrb ::= SEQUENCE {
	toe-nav								BIT STRING (SIZE (14)),
	ganss-omega-nav						BIT STRING (SIZE (32)),
	delta-n-nav							BIT STRING (SIZE (16)),
	m-zero-nav							BIT STRING (SIZE (32)),
	omegadot-nav						BIT STRING (SIZE (24)),
	ganss-e-nav							BIT STRING (SIZE (32)),
	idot-nav							BIT STRING (SIZE (14)),
	a-sqrt-nav							BIT STRING (SIZE (32)),
	i-zero-nav							BIT STRING (SIZE (32)),
	omega-zero-nav						BIT STRING (SIZE (32)),
	c-rs-nav							BIT STRING (SIZE (16)),
	c-is-nav							BIT STRING (SIZE (16)),
	c-us-nav							BIT STRING (SIZE (16)),
	c-rc-nav							BIT STRING (SIZE (16)),
	c-ic-nav 							BIT STRING (SIZE (16)),
	c-uc-nav							BIT STRING (SIZE (16)),
	ie-Extensions		 				ProtocolExtensionContainer { { GANSS-KeplerianParametersOrb-ExtIEs } }		OPTIONAL,
	...
}

GANSS-KeplerianParametersOrb-ExtIEs NBAP-PROTOCOL-EXTENSION ::= {
	...
}

GANSS-NAVclockModel ::= SEQUENCE {
	navToc					BIT STRING (SIZE (16)),
	navaf2					BIT STRING (SIZE (8)),
	navaf1					BIT STRING (SIZE (16)),
	navaf0					BIT STRING (SIZE (22)),
	navTgd					BIT STRING (SIZE (8)),
	ie-Extensions			ProtocolExtensionContainer { { GANSS-NAVclockModel-ExtIEs } }	OPTIONAL,
	...
}

GANSS-NAVclockModel-ExtIEs NBAP-PROTOCOL-EXTENSION ::= {
	...
}

GANSS-Navigation-Model-And-Time-Recovery ::= SEQUENCE {
	ganss-Transmission-Time		GANSS-Transmission-Time,
	non-broadcastIndication		ENUMERATED{true}		OPTIONAL,
	ganssSatInfoNav				GANSS-Sat-Info-Nav,
	ie-Extensions				ProtocolExtensionContainer { { GANSS-Navigation-Model-And-Time-Recovery-ExtIEs } } OPTIONAL,
	...
}

GANSS-Navigation-Model-And-Time-Recovery-ExtIEs NBAP-PROTOCOL-EXTENSION ::= {
	...
}


GANSS-NavModel-CNAVKeplerianSet ::= SEQUENCE {
	cnavTop					BIT STRING (SIZE (11)),
	cnavURAindex			BIT STRING (SIZE (5)),
	cnavDeltaA				BIT STRING (SIZE (26)),
	cnavAdot				BIT STRING (SIZE (25)),
	cnavDeltaNo				BIT STRING (SIZE (17)),
	cnavDeltaNoDot			BIT STRING (SIZE (23)),
	cnavMo					BIT STRING (SIZE (33)),
	cnavE					BIT STRING (SIZE (33)),
	cnavOmega				BIT STRING (SIZE (33)),
	cnavOMEGA0				BIT STRING (SIZE (33)),
	cnavDeltaOmegaDot		BIT STRING (SIZE (17)),
	cnavIo					BIT STRING (SIZE (33)),
	cnavIoDot				BIT STRING (SIZE (15)),
	cnavCis					BIT STRING (SIZE (16)),
	cnavCic					BIT STRING (SIZE (16)),
	cnavCrs					BIT STRING (SIZE (24)),
	cnavCrc					BIT STRING (SIZE (24)),
	cnavCus					BIT STRING (SIZE (21)),
	cnavCuc					BIT STRING (SIZE (21)),
	ie-Extensions			ProtocolExtensionContainer { { GANSS-NavModel-CNAVKeplerianSet-ExtIEs } }	OPTIONAL,
	...
}

GANSS-NavModel-CNAVKeplerianSet-ExtIEs NBAP-PROTOCOL-EXTENSION ::= {
	...
}

GANSS-NavModel-GLONASSecef ::= SEQUENCE {
	gloEn					BIT STRING (SIZE (5)),
	gloP1					BIT STRING (SIZE(2)),
	gloP2					BIT STRING (SIZE (1)),
	gloM					BIT STRING (SIZE (2))																			OPTIONAL,
	gloX					BIT STRING (SIZE (27)),
	gloXdot					BIT STRING (SIZE (24)),
	gloXdotdot				BIT STRING (SIZE (5)),
	gloY					BIT STRING (SIZE (27)),
	gloYdot					BIT STRING (SIZE (24)),
	gloYdotdot				BIT STRING (SIZE (5)),
	gloZ					BIT STRING (SIZE (27)),
	gloZdot					BIT STRING (SIZE (24)),
	gloZdotdot				BIT STRING (SIZE (5)),
	ie-Extensions			ProtocolExtensionContainer { { GANSS-NavModel-GLONASSecef-ExtIEs } }	OPTIONAL,
	...
}

GANSS-NavModel-GLONASSecef-ExtIEs NBAP-PROTOCOL-EXTENSION ::= {
	...
}


GANSS-NavModel-NAVKeplerianSet ::= SEQUENCE {
	navURA					BIT STRING (SIZE (4)),
	navFitFlag				BIT STRING (SIZE (1)),
	navToe					BIT STRING (SIZE (16)),
	navOmega				BIT STRING (SIZE (32)),
	navDeltaN				BIT STRING (SIZE (16)),
	navM0					BIT STRING (SIZE (32)),
	navOmegaADot			BIT STRING (SIZE (24)),
	navE					BIT STRING (SIZE (32)),
	navIDot					BIT STRING (SIZE (14)),
	navAPowerHalf			BIT STRING (SIZE (32)),
	navI0					BIT STRING (SIZE (32)),
	navOmegaA0				BIT STRING (SIZE (32)),
	navCrs					BIT STRING (SIZE (16)),
	navCis					BIT STRING (SIZE (16)),
	navCus					BIT STRING (SIZE (16)),
	navCrc					BIT STRING (SIZE (16)),
	navCic					BIT STRING (SIZE (16)),
	navCuc					BIT STRING (SIZE (16)),
	ie-Extensions			ProtocolExtensionContainer { { GANSS-NavModel-NAVKeplerianSet-ExtIEs } }	OPTIONAL,
	...
}

GANSS-NavModel-NAVKeplerianSet-ExtIEs NBAP-PROTOCOL-EXTENSION ::= {
	...
}

GANSS-NavModel-SBASecef ::= SEQUENCE {
	-- The following IE shall be present if 'GANSS-SBASclockModel' in 'GANSS-AddClockModels' is not included in 'Ganss-Sat-Info-AddNavList'
	sbasTo					BIT STRING (SIZE (13))												OPTIONAL,
	sbasAccuracy			BIT STRING (SIZE (4)),
	sbasXg					BIT STRING (SIZE (30)),
	sbasYg					BIT STRING (SIZE (30)),
	sbasZg					BIT STRING (SIZE (25)),
	sbasXgDot				BIT STRING (SIZE (17)),
	sbasYgDot				BIT STRING (SIZE (17)),
	sbasZgDot				BIT STRING (SIZE (18)),
	sbasXgDotDot			BIT STRING (SIZE (10)),
	sbagYgDotDot			BIT STRING (SIZE (10)),
	sbasZgDotDot			BIT STRING (SIZE (10)),
	ie-Extensions			ProtocolExtensionContainer { { GANSS-NavModel-SBASecef-ExtIEs } }	OPTIONAL,
	...
}

GANSS-NavModel-SBASecef-ExtIEs NBAP-PROTOCOL-EXTENSION ::= {
	...
}

GANSS-Orbit-Model ::= CHOICE {
	gANSS-keplerianParameters			GANSS-KeplerianParametersOrb,
	...
}

GANSS-Real-Time-Integrity ::= SEQUENCE (SIZE (1..maxGANSSSat)) OF GANSS-RealTimeInformationItem

GANSS-RealTimeInformationItem ::= SEQUENCE {
	bad-ganss-satId						INTEGER(0..63),
	bad-ganss-signalId					BIT STRING(SIZE(8))											OPTIONAL,
	ie-Extensions						ProtocolExtensionContainer { { GANSS-RealTimeInformationItem-ExtIEs } }	OPTIONAL,
	...
}

GANSS-RealTimeInformationItem-ExtIEs NBAP-PROTOCOL-EXTENSION ::= {
	...
}

GANSS-RX-Pos ::= SEQUENCE {
	latitudeSign						ENUMERATED{north,south},
	degreesOfLatitude					INTEGER(0..2147483647),
	degreesOfLongitude					INTEGER(-2147483648..2147483647),
	directionOfAltitude					ENUMERATED{height,depth},
	altitude							INTEGER(0..32767),
	ie-Extensions						ProtocolExtensionContainer { { GANSS-RX-Pos-ExtIEs } }	OPTIONAL,
	...
}

GANSS-RX-Pos-ExtIEs NBAP-PROTOCOL-EXTENSION ::= {
	...
}

GANSS-SatelliteClockModelItem ::= SEQUENCE {
	t-oc								BIT STRING (SIZE (14)),
	a-i2								BIT STRING (SIZE (12)),
	a-i1								BIT STRING (SIZE (18)),
	a-i0								BIT STRING (SIZE (28)),
	t-gd								BIT STRING (SIZE (10))										OPTIONAL,
	model-id							INTEGER(0..1,...)											OPTIONAL,
	ie-Extensions						ProtocolExtensionContainer { { GANSS-SatelliteClockModelItem-ExtIEs } }	OPTIONAL,
	...
}

GANSS-SatelliteClockModelItem-ExtIEs NBAP-PROTOCOL-EXTENSION ::= {
	...
}

GANSS-SatelliteInformationKP ::= SEQUENCE (SIZE (1..maxGANSSSatAlmanac)) OF GANSS-SatelliteInformationKPItem

GANSS-SatelliteInformationKPItem ::= SEQUENCE {
	satId								INTEGER(0..63),
	ganss-e-alm							BIT STRING (SIZE (11)),
	ganss-delta-I-alm					BIT STRING (SIZE (11)),
	ganss-omegadot-alm					BIT STRING (SIZE (11)),
	ganss-svhealth-alm					BIT STRING (SIZE (4)),
	ganss-delta-a-sqrt-alm				BIT STRING (SIZE (17)),
	ganss-omegazero-alm					BIT STRING (SIZE (16)),
	ganss-m-zero-alm					BIT STRING (SIZE (16)),
	ganss-omega-alm						BIT STRING (SIZE (16)),
	ganss-af-zero-alm					BIT STRING (SIZE (14)),
	ganss-af-one-alm 					BIT STRING (SIZE (11)),
	ie-Extensions						ProtocolExtensionContainer { { GANSS-SatelliteInformationKPItem-ExtIEs } }	OPTIONAL,
	...
}

GANSS-SatelliteInformationKPItem-ExtIEs NBAP-PROTOCOL-EXTENSION ::= {
	...
}

Ganss-Sat-Info-AddNavList ::= SEQUENCE (SIZE (1..maxGANSSSat)) OF SEQUENCE {
	satId						INTEGER (0..63),
	svHealth					BIT STRING (SIZE (6)),
	iod							BIT STRING (SIZE (11)),
	ganssAddClockModels			GANSS-AddClockModels,
	ganssAddOrbitModels			GANSS-AddOrbitModels,
	ie-Extensions				ProtocolExtensionContainer { { Ganss-Sat-Info-AddNavList-ExtIEs } } OPTIONAL,
	...
}

Ganss-Sat-Info-AddNavList-ExtIEs NBAP-PROTOCOL-EXTENSION ::= {
	...
}

GANSS-SAT-Info-Almanac-GLOkpList ::= SEQUENCE (SIZE (1.. maxGANSSSatAlmanac)) OF GANSS-SAT-Info-Almanac-GLOkp

GANSS-SAT-Info-Almanac-GLOkp ::= SEQUENCE {
	gloAlmNA				BIT STRING (SIZE(11)),
	gloAlmnA				BIT STRING (SIZE(5)),
	gloAlmHA				BIT STRING (SIZE(5)),
	gloAlmLambdaA			BIT STRING (SIZE(21)),
	gloAlmTlambdaA			BIT STRING (SIZE(21)),
	gloAlmDeltaIA			BIT STRING (SIZE(18)),
	gloAkmDeltaTA			BIT STRING (SIZE(22)),
	gloAlmDeltaTdotA		BIT STRING (SIZE(7)),
	gloAlmEpsilonA			BIT STRING (SIZE(15)),
	gloAlmOmegaA			BIT STRING (SIZE(16)),
	gloAlmTauA				BIT STRING (SIZE(10)),
	gloAlmCA				BIT STRING (SIZE(1)),
	gloAlmMA				BIT STRING (SIZE(2)) 																			OPTIONAL,
	ie-Extensions			ProtocolExtensionContainer { { GANSS-SAT-Info-Almanac-GLOkp-ExtIEs } }	OPTIONAL,
	...
}

GANSS-SAT-Info-Almanac-GLOkp-ExtIEs NBAP-PROTOCOL-EXTENSION ::= {
	...
}

GANSS-SAT-Info-Almanac-MIDIkpList ::= SEQUENCE (SIZE (1.. maxGANSSSatAlmanac)) OF GANSS-SAT-Info-Almanac-MIDIkp

GANSS-SAT-Info-Almanac-MIDIkp ::= SEQUENCE {
	svID					INTEGER(0..63),
	midiAlmE				BIT STRING (SIZE (11)),
	midiAlmDeltaI			BIT STRING (SIZE (11)),
	midiAlmOmegaDot			BIT STRING (SIZE (11)),
	midiAlmSqrtA			BIT STRING (SIZE (17)),
	midiAlmOmega0			BIT STRING (SIZE (16)),
	midiAlmOmega			BIT STRING (SIZE (16)),
	midiAlmMo				BIT STRING (SIZE (16)),
	midiAlmaf0				BIT STRING (SIZE (11)),
	midiAlmaf1				BIT STRING (SIZE (10)),
	midiAlmL1Health			BIT STRING (SIZE (1)),
	midiAlmL2Health			BIT STRING (SIZE (1)),
	midiAlmL5Health			BIT STRING (SIZE (1)),
	ie-Extensions			ProtocolExtensionContainer { { GANSS-SAT-Info-Almanac-MIDIkp-ExtIEs } }	OPTIONAL,
	...
}

GANSS-SAT-Info-Almanac-MIDIkp-ExtIEs NBAP-PROTOCOL-EXTENSION ::= {
	...
}

GANSS-SAT-Info-Almanac-NAVkpList ::= SEQUENCE (SIZE (1.. maxGANSSSatAlmanac)) OF GANSS-SAT-Info-Almanac-NAVkp

GANSS-SAT-Info-Almanac-NAVkp ::= SEQUENCE {
	svID					INTEGER(0..63),
	navAlmE					BIT STRING (SIZE (16)),
	navAlmDeltaI			BIT STRING (SIZE (16)),
	navAlmOMEGADOT			BIT STRING (SIZE (16)),
	navAlmSVHealth			BIT STRING (SIZE (8)),
	navAlmSqrtA				BIT STRING (SIZE (24)),
	navAlmOMEGAo			BIT STRING (SIZE (24)),
	navAlmOmega				BIT STRING (SIZE (24)),
	navAlmMo				BIT STRING (SIZE (24)),
	navAlmaf0				BIT STRING (SIZE (11)),
	navAlmaf1				BIT STRING (SIZE (11)),
	ie-Extensions			ProtocolExtensionContainer { { GANSS-SAT-Info-Almanac-NAVkp-ExtIEs } }	OPTIONAL,
	...
}

GANSS-SAT-Info-Almanac-NAVkp-ExtIEs NBAP-PROTOCOL-EXTENSION ::= {
	...
}

GANSS-SAT-Info-Almanac-REDkpList ::= SEQUENCE (SIZE (1.. maxGANSSSatAlmanac)) OF GANSS-SAT-Info-Almanac-REDkp

GANSS-SAT-Info-Almanac-REDkp ::= SEQUENCE {
	svID					INTEGER(0..63),
	redAlmDeltaA			BIT STRING (SIZE (8)),
	redAlmOmega0			BIT STRING (SIZE (7)),
	redAlmPhi0				BIT STRING (SIZE (7)),
	redAlmL1Health			BIT STRING (SIZE (1)),
	redAlmL2Health			BIT STRING (SIZE (1)),
	redAlmL5Health			BIT STRING (SIZE (1)),
	ie-Extensions			ProtocolExtensionContainer { { GANSS-SAT-Info-Almanac-REDkp-ExtIEs } }	OPTIONAL,
	...
}

GANSS-SAT-Info-Almanac-REDkp-ExtIEs NBAP-PROTOCOL-EXTENSION ::= {
	...
}

GANSS-SAT-Info-Almanac-SBASecefList ::=	SEQUENCE (SIZE (1.. maxGANSSSatAlmanac)) OF GANSS-SAT-Info-Almanac-SBASecef

GANSS-SAT-Info-Almanac-SBASecef ::=	SEQUENCE {
	sbasAlmDataID			BIT STRING (SIZE(2)),
	svID					INTEGER(0..63),
	sbasAlmHealth			BIT STRING (SIZE(8)),
	sbasAlmXg				BIT STRING (SIZE(15)),
	sbasAlmYg				BIT STRING (SIZE(15)),
	sbasAlmZg				BIT STRING (SIZE(9)),
	sbasAlmXgdot			BIT STRING (SIZE(3)),
	sbasAlmYgDot			BIT STRING (SIZE(3)),
	sbasAlmZgDot			BIT STRING (SIZE(4)),
	sbasAlmTo				BIT STRING (SIZE(11)),
	ie-Extensions			ProtocolExtensionContainer { { GANSS-SAT-Info-Almanac-SBASecef-ExtIEs } }	OPTIONAL,
	...
}

GANSS-SAT-Info-Almanac-SBASecef-ExtIEs NBAP-PROTOCOL-EXTENSION ::= {
	...
}


GANSS-Sat-Info-Nav ::= SEQUENCE (SIZE(1..maxGANSSSat)) OF SEQUENCE {
	satId						INTEGER(0..63),
	svHealth					BIT STRING (SIZE(5)),
	iod							BIT STRING (SIZE(10)),
	ganssClockModel				GANSS-Clock-Model,
	ganssOrbitModel				GANSS-Orbit-Model,
	ie-Extensions				ProtocolExtensionContainer { { GANSS-Sat-Info-Nav-ExtIEs } } OPTIONAL,
	...
}

GANSS-Sat-Info-Nav-ExtIEs NBAP-PROTOCOL-EXTENSION ::= {
	...
}


GANSS-SBAS-ID ::= ENUMERATED 	{
								waas,
								egnos,
								msas,
								gagan,
								...
								}

GANSS-SBASclockModel ::= SEQUENCE {
	sbasTo					BIT STRING (SIZE (13)),
	sbasAgfo				BIT STRING (SIZE (12)),
	sbasAgf1				BIT STRING (SIZE (8)),
	ie-Extensions			ProtocolExtensionContainer { { GANSS-SBASclockModel-ExtIEs } }	OPTIONAL,
	...
}

GANSS-SBASclockModel-ExtIEs NBAP-PROTOCOL-EXTENSION ::= {
	...
}

GANSS-Signal-ID ::= INTEGER(0..7,...)

GANSS-StatusHealth ::= ENUMERATED {
	udre-scale-1dot0,
	udre-scale-0dot75,
	udre-scale-0dot5,
	udre-scale-0dot3,
	udre-scale-0dot2,
	udre-scale-0dot1,
	no-data,
	invalid-data
}

GANSS-Time-ID	::= INTEGER(0..7,...)

GANSS-Time-Model ::= SEQUENCE {
	ganss-time-model-Ref-Time			INTEGER(0..37799),
	ganss-t-a0							INTEGER(-2147483648.. 2147483647),
	ganss-t-a1							INTEGER(-8388608.. 8388607)									OPTIONAL,
	ganss-t-a2							INTEGER(-64..63)											OPTIONAL,
	gnss-to-id							ENUMERATED{gps,...,galileo,qzss,glonass},
	ganss-wk-number						INTEGER(0..8191)											OPTIONAL,
	ie-Extensions						ProtocolExtensionContainer { { GANSS-Time-Model-ExtIEs } }	OPTIONAL,
	...
}

GANSS-Time-Model-ExtIEs NBAP-PROTOCOL-EXTENSION ::= {
	...
}

GANSS-Transmission-Time ::= SEQUENCE {
	ganssDay					INTEGER(0..8191)																			OPTIONAL,
	ganssTod					INTEGER(0..86399),
	ie-Extensions				ProtocolExtensionContainer { { GANSS-Transmission-Time-ExtIEs } } 						OPTIONAL,
	...
}

GANSS-Transmission-Time-ExtIEs NBAP-PROTOCOL-EXTENSION ::= {
	...
}

GANSS-UTC-Model ::= SEQUENCE {
	a-one-utc							BIT STRING (SIZE (24)),
	a-zero-utc							BIT STRING (SIZE (32)),
	t-ot-utc							BIT STRING (SIZE (8)),
	w-n-t-utc							BIT STRING (SIZE (8)),
	delta-t-ls-utc						BIT STRING (SIZE (8)),
	w-n-lsf-utc							BIT STRING (SIZE (8)),
	dn-utc								BIT STRING (SIZE (8)),
	delta-t-lsf-utc						BIT STRING (SIZE (8)),
	ie-Extensions						ProtocolExtensionContainer { { GANSS-UTC-Model-ExtIEs } }	OPTIONAL,
	...
}

GANSS-UTC-Model-ExtIEs NBAP-PROTOCOL-EXTENSION ::= {
	...
}

GANSS-UTCmodelSet1 ::= SEQUENCE {
	utcA0				BIT STRING (SIZE(16)),
	utcA1				BIT STRING (SIZE(13)),
	utcA2				BIT STRING (SIZE(7)),
	utcDeltaTls			BIT STRING (SIZE(8)),
	utcTot				BIT STRING (SIZE(16)),
	utcWNot				BIT STRING (SIZE(13)),
	utcWNlsf			BIT STRING (SIZE(8)),
	utcDN				BIT STRING (SIZE(4)),
	utcDeltaTlsf		BIT STRING (SIZE(8)),
	ie-Extensions		ProtocolExtensionContainer { { GANSS-UTCmodelSet1-ExtIEs } }	OPTIONAL,
	...
}

GANSS-UTCmodelSet1-ExtIEs NBAP-PROTOCOL-EXTENSION ::= {
	...
}

GANSS-UTCmodelSet2 ::= SEQUENCE {
	nA					BIT STRING (SIZE(11)),
	tauC				BIT STRING (SIZE(32)),
	deltaUT1			GANSS-DeltaUT1													OPTIONAL,
	kp					BIT STRING (SIZE(2)) 											OPTIONAL,
	ie-Extensions		ProtocolExtensionContainer { { GANSS-UTCmodelSet2-ExtIEs } }	OPTIONAL,
	...
}

GANSS-UTCmodelSet2-ExtIEs NBAP-PROTOCOL-EXTENSION ::= {
	...
}

GANSS-UTCmodelSet3 ::= SEQUENCE {
	utcA1wnt			BIT STRING (SIZE(24)),
	utcA0wnt			BIT STRING (SIZE(32)),
	utcTot				BIT STRING (SIZE(8)),
	utcWNt				BIT STRING (SIZE(8)),
	utcDeltaTls			BIT STRING (SIZE(8)),
	utcWNlsf			BIT STRING (SIZE(8)),
	utcDN				BIT STRING (SIZE(8)),
	utcDeltaTlsf		BIT STRING (SIZE(8)),
	utcStandardID		BIT STRING (SIZE(3)),
	ie-Extensions		ProtocolExtensionContainer { { GANSS-UTCmodelSet3-ExtIEs } }	OPTIONAL,
	...
}

GANSS-UTCmodelSet3-ExtIEs NBAP-PROTOCOL-EXTENSION ::= {
	...
}

GapLength				::= INTEGER (1..14)
-- Unit slot

GapDuration				::= INTEGER (1..144,...)
-- Unit frame

GenericTrafficCategory	::= BIT STRING (SIZE (8))

GPS-Almanac ::= SEQUENCE {
    wna-alm              BIT STRING (SIZE (8)),
     sat-info-almanac     SAT-Info-Almanac,
	sVGlobalHealth-alm	BIT STRING (SIZE (364))	OPTIONAL,
    ie-Extensions		 ProtocolExtensionContainer { { GPS-Almanac-ExtIEs} }		OPTIONAL,
   ...
}

GPS-Almanac-ExtIEs NBAP-PROTOCOL-EXTENSION ::= {
	{ ID id-SAT-Info-Almanac-ExtItem	CRITICALITY	ignore		EXTENSION 	SAT-Info-Almanac-ExtList			PRESENCE	optional},
	...
}

GPS-Ionospheric-Model ::= SEQUENCE {
   alpha-zero-ionos      BIT STRING (SIZE (8)),
   alpha-one-ionos       BIT STRING (SIZE (8)),
   alpha-two-ionos       BIT STRING (SIZE (8)),
   alpha-three-ionos     BIT STRING (SIZE (8)),
   beta-zero-ionos       BIT STRING (SIZE (8)),
   beta-one-ionos        BIT STRING (SIZE (8)),
   beta-two-ionos        BIT STRING (SIZE (8)),
   beta-three-ionos      BIT STRING (SIZE (8)),
   ie-Extensions		 ProtocolExtensionContainer { { GPS-Ionospheric-Model-ExtIEs} }		OPTIONAL,
   ...
}

GPS-Ionospheric-Model-ExtIEs NBAP-PROTOCOL-EXTENSION ::= {
	...
}

GPS-Information ::= SEQUENCE (SIZE (0..maxNoGPSItems)) OF GPS-Information-Item
-- This IE shall be present if the Information Type Item IE indicates 'GPS Information'

GPS-Information-Item ::= ENUMERATED {
   gps-navigation-model-and-time-recovery,
   gps-ionospheric-model,
   gps-utc-model,
   gps-almanac,
   gps-rt-integrity,
   ...
}

GPS-RealTime-Integrity ::= CHOICE {
	bad-satellites		        GPSBadSat-Info-RealTime-Integrity,
	no-bad-satellites           NULL
}

GPSBadSat-Info-RealTime-Integrity ::= SEQUENCE {
	sat-info		                SATInfo-RealTime-Integrity,
	ie-Extensions					ProtocolExtensionContainer { { GPSBadSat-Info-RealTime-Integrity-ExtIEs} }		OPTIONAL,
	...
}

GPSBadSat-Info-RealTime-Integrity-ExtIEs NBAP-PROTOCOL-EXTENSION ::= {
	...
}

GPS-NavigationModel-and-TimeRecovery ::= SEQUENCE (SIZE (1..maxNoSat)) OF GPS-NavandRecovery-Item

GPS-NavandRecovery-Item ::= SEQUENCE {
  tx-tow-nav                       INTEGER (0..1048575),
  sat-id-nav                       SAT-ID,
  tlm-message-nav                  BIT STRING (SIZE (14)),
  tlm-revd-c-nav                   BIT STRING (SIZE (2)),
  ho-word-nav                      BIT STRING (SIZE (22)),
  w-n-nav                          BIT STRING (SIZE (10)),
  ca-or-p-on-l2-nav                BIT STRING (SIZE (2)),
  user-range-accuracy-index-nav    BIT STRING (SIZE (4)),
  sv-health-nav                    BIT STRING (SIZE (6)),
  iodc-nav                         BIT STRING (SIZE (10)),
  l2-p-dataflag-nav                BIT STRING (SIZE (1)),
  sf1-reserved-nav                 BIT STRING (SIZE (87)),
  t-gd-nav                         BIT STRING (SIZE (8)),
  t-oc-nav                         BIT STRING (SIZE (16)),
  a-f-2-nav                        BIT STRING (SIZE (8)),
  a-f-1-nav                        BIT STRING (SIZE (16)),
  a-f-zero-nav                     BIT STRING (SIZE (22)),
  c-rs-nav                         BIT STRING (SIZE (16)),
  delta-n-nav                      BIT STRING (SIZE (16)),
  m-zero-nav                       BIT STRING (SIZE (32)),
  c-uc-nav                         BIT STRING (SIZE (16)),
  gps-e-nav                        BIT STRING (SIZE (32)),
  c-us-nav                         BIT STRING (SIZE (16)),
  a-sqrt-nav                       BIT STRING (SIZE (32)),
  t-oe-nav                         BIT STRING (SIZE (16)),
  fit-interval-flag-nav            BIT STRING (SIZE (1)),
  aodo-nav                         BIT STRING (SIZE (5)),
  c-ic-nav                         BIT STRING (SIZE (16)),
  omega-zero-nav                   BIT STRING (SIZE (32)),
  c-is-nav                         BIT STRING (SIZE (16)),
  i-zero-nav                       BIT STRING (SIZE (32)),
  c-rc-nav                         BIT STRING (SIZE (16)),
  gps-omega-nav                    BIT STRING (SIZE (32)),
  omegadot-nav                     BIT STRING (SIZE (24)),
  idot-nav                         BIT STRING (SIZE (14)),
  spare-zero-fill                  BIT STRING (SIZE (20)),
  ie-Extensions		               ProtocolExtensionContainer { { GPS-NavandRecovery-Item-ExtIEs} }		OPTIONAL,
   ...
}

GPS-NavandRecovery-Item-ExtIEs NBAP-PROTOCOL-EXTENSION ::= {
	...
}


GPS-RX-POS ::= SEQUENCE {
    latitudeSign		    ENUMERATED {north, south},
	latitude			    INTEGER (0..8388607),
	longitude			    INTEGER (-8388608..8388607),
	directionOfAltitude		ENUMERATED {height, depth},
	altitude				INTEGER (0..32767),
	iE-Extensions			ProtocolExtensionContainer { { GPS-RX-POS-ExtIEs} } OPTIONAL,
	...
}

GPS-RX-POS-ExtIEs NBAP-PROTOCOL-EXTENSION ::= {
	...
}

GPS-Status-Health ::= ENUMERATED {
   udre-scale-1dot0,
   udre-scale-0dot75,
   udre-scale-0dot5,
   udre-scale-0dot3,
   udre-scale-0dot1,
   no-data,
   invalid-data
}

GPSTOW ::= INTEGER (0..604799)

GPS-UTC-Model ::= SEQUENCE {
   a-one-utc             BIT STRING (SIZE (24)),
   a-zero-utc            BIT STRING (SIZE (32)),
   t-ot-utc              BIT STRING (SIZE (8)),
   delta-t-ls-utc        BIT STRING (SIZE (8)),
   w-n-t-utc             BIT STRING (SIZE (8)),
   w-n-lsf-utc           BIT STRING (SIZE (8)),
   dn-utc                BIT STRING (SIZE (8)),
   delta-t-lsf-utc       BIT STRING (SIZE (8)),
   ie-Extensions		 ProtocolExtensionContainer { { GPS-UTC-Model-ExtIEs} }		OPTIONAL,
   ...
}

GPS-UTC-Model-ExtIEs NBAP-PROTOCOL-EXTENSION ::= {
	...
}

-- ==========================================
--	H
-- ==========================================

HARQ-Info-for-E-DCH ::= ENUMERATED {
	rv0,
	rvtable
}

HARQ-MemoryPartitioning	::= CHOICE {
	implicit		HARQ-MemoryPartitioning-Implicit,
	explicit		HARQ-MemoryPartitioning-Explicit,
	...
	}

HARQ-MemoryPartitioning-Implicit	::= SEQUENCE {
	number-of-Processes			INTEGER (1..8,...,12|14|16),
	iE-Extensions				ProtocolExtensionContainer { { HARQ-MemoryPartitioning-Implicit-ExtIEs } }			OPTIONAL,
	...
}

HARQ-MemoryPartitioning-Implicit-ExtIEs NBAP-PROTOCOL-EXTENSION ::= {
	...
}

HARQ-MemoryPartitioning-Explicit	::= SEQUENCE {
	hARQ-MemoryPartitioningList			HARQ-MemoryPartitioningList,
	iE-Extensions						ProtocolExtensionContainer { { HARQ-MemoryPartitioning-Explicit-ExtIEs } }			OPTIONAL,
	...
}

HARQ-MemoryPartitioning-Explicit-ExtIEs NBAP-PROTOCOL-EXTENSION ::= {
-- The following IE may only be used in FDD, in MIMO dual stream transmission mode
	{ID id-HARQ-MemoryPartitioningInfoExtForMIMO	CRITICALITY ignore	EXTENSION HARQ-MemoryPartitioningInfoExtForMIMO	PRESENCE optional},
	...
}

HARQ-MemoryPartitioningList	::= SEQUENCE (SIZE (1..maxNrOfHARQProcesses)) OF HARQ-MemoryPartitioningItem

HARQ-MemoryPartitioningInfoExtForMIMO ::= SEQUENCE (SIZE (4|6|8)) OF HARQ-MemoryPartitioningItem

HARQ-MemoryPartitioningItem ::= SEQUENCE {
	process-Memory-Size					ENUMERATED {
										hms800, hms1600, hms2400, hms3200, hms4000,
										hms4800, hms5600, hms6400, hms7200, hms8000,
										hms8800, hms9600, hms10400, hms11200, hms12000,
										hms12800, hms13600, hms14400, hms15200, hms16000,
										hms17600, hms19200, hms20800, hms22400, hms24000,
										hms25600, hms27200, hms28800, hms30400, hms32000,
										hms36000, hms40000, hms44000, hms48000, hms52000,
										hms56000, hms60000, hms64000, hms68000, hms72000,
										hms76000, hms80000, hms88000, hms96000, hms104000,
										hms112000, hms120000, hms128000, hms136000, hms144000,
										hms152000, hms160000, hms176000, hms192000, hms208000,
										hms224000, hms240000, hms256000, hms272000, hms288000,
										hms304000,...},
	iE-Extensions						ProtocolExtensionContainer { { HARQ-MemoryPartitioningItem-ExtIEs } }			OPTIONAL,
	...
}

HARQ-MemoryPartitioningItem-ExtIEs NBAP-PROTOCOL-EXTENSION ::= {
	...
}

HARQ-Preamble-Mode ::= ENUMERATED {
mode0,
mode1
}


HARQ-Process-Allocation-2ms-EDCH ::= BIT STRING ( SIZE(maxNrOfEDCHHARQProcesses2msEDCH) )

HARQ-Preamble-Mode-Activation-Indicator	::=ENUMERATED	{
	harqPreambleModeActivated
}

HSDPA-Capability ::= ENUMERATED {hsdpa-capable, hsdpa-non-capable}

HS-DSCHProvidedBitRate ::= SEQUENCE (SIZE (1..maxNrOfPriorityClasses)) OF HS-DSCHProvidedBitRate-Item

HS-DSCHProvidedBitRate-Item ::= SEQUENCE {
	schedulingPriorityIndicator			SchedulingPriorityIndicator,
	hS-DSCHProvidedBitRateValue			HS-DSCHProvidedBitRateValue,
	iE-Extensions						ProtocolExtensionContainer { { HS-DSCHProvidedBitRate-Item-ExtIEs} }		OPTIONAL,
	...
}

HS-DSCHProvidedBitRate-Item-ExtIEs NBAP-PROTOCOL-EXTENSION ::= {
	...
}

HS-DSCHProvidedBitRateValue ::= INTEGER(0..16777215,...,16777216..256000000)
-- except for 7.68Mcps TDD Unit bit/s, Range 0..2^24-1..2^24..256,000,000, Step 1 bit
-- 7.68Mcps TDD Unit 2bit/s, Range 0..2^24-1..2^24..256,000,000, Step 1


HS-DSCHProvidedBitRateValueInformation-For-CellPortion ::= SEQUENCE (SIZE (1..maxNrOfCellPortionsPerCell)) OF HS-DSCHProvidedBitRateValueInformation-For-CellPortion-Item

HS-DSCHProvidedBitRateValueInformation-For-CellPortion-Item ::= SEQUENCE{
	cellPortionID					CellPortionID,
	hS-DSCHProvidedBitRateValue		HS-DSCHProvidedBitRate,
	iE-Extensions					ProtocolExtensionContainer { {HS-DSCHProvidedBitRateValueInformation-For-CellPortion-Item-ExtIEs} }	OPTIONAL,
	...
}

HS-DSCHProvidedBitRateValueInformation-For-CellPortion-Item-ExtIEs NBAP-PROTOCOL-EXTENSION ::= {
	...
}

HS-DSCHProvidedBitRateValueInformation-For-CellPortionLCR ::= SEQUENCE (SIZE (1..maxNrOfCellPortionsPerCellLCR)) OF HS-DSCHProvidedBitRateValueInformation-For-CellPortionLCR-Item

HS-DSCHProvidedBitRateValueInformation-For-CellPortionLCR-Item ::= SEQUENCE{
	cellPortionLCRID					CellPortionLCRID,
	hS-DSCHProvidedBitRateValue		HS-DSCHProvidedBitRate,
	iE-Extensions					ProtocolExtensionContainer { {HS-DSCHProvidedBitRateValueInformation-For-CellPortionLCR-Item-ExtIEs} }	OPTIONAL,
	...
}

HS-DSCHProvidedBitRateValueInformation-For-CellPortionLCR-Item-ExtIEs NBAP-PROTOCOL-EXTENSION ::= {
	...
}

HS-DSCHRequiredPower ::= SEQUENCE (SIZE (1..maxNrOfPriorityClasses)) OF HS-DSCHRequiredPower-Item

HS-DSCHRequiredPower-Item ::= SEQUENCE {
	schedulingPriorityIndicator				SchedulingPriorityIndicator,
	hS-DSCHRequiredPowerValue				HS-DSCHRequiredPowerValue,
	hS-DSCHRequiredPowerPerUEInformation	HS-DSCHRequiredPowerPerUEInformation						OPTIONAL,
	iE-Extensions							ProtocolExtensionContainer { { HS-DSCHRequiredPower-Item-ExtIEs} }		OPTIONAL,
	...
}

HS-DSCHRequiredPower-Item-ExtIEs NBAP-PROTOCOL-EXTENSION ::= {
	...
}

HS-DSCHRequiredPowerValue ::= INTEGER(0..1000)
-- Unit %, Range 0 ..1000, Step 0.1%

HS-DSCHRequiredPowerPerUEInformation ::= SEQUENCE (SIZE (1.. maxNrOfContextsOnUeList)) OF HS-DSCHRequiredPowerPerUEInformation-Item


HS-DSCHRequiredPowerPerUEInformation-Item ::= SEQUENCE {
	cRNC-CommunicationContextID				CRNC-CommunicationContextID,
	hS-DSCHRequiredPowerPerUEWeight			HS-DSCHRequiredPowerPerUEWeight		OPTIONAL,
	iE-Extensions							ProtocolExtensionContainer { { HS-DSCHRequiredPowerPerUEInformation-Item-ExtIEs} }		OPTIONAL,
	...
}

HS-DSCHRequiredPowerPerUEInformation-Item-ExtIEs NBAP-PROTOCOL-EXTENSION ::= {
	...
}

HS-DSCHRequiredPowerPerUEWeight ::= INTEGER(0..100)
-- Unit %, Range 0 ..100, Step 1%

HS-DSCHRequiredPowerValueInformation-For-CellPortion ::= SEQUENCE (SIZE (1..maxNrOfCellPortionsPerCell)) OF HS-DSCHRequiredPowerValueInformation-For-CellPortion-Item

HS-DSCHRequiredPowerValueInformation-For-CellPortion-Item ::= SEQUENCE{
	cellPortionID				CellPortionID,
	hS-DSCHRequiredPowerValue	HS-DSCHRequiredPower,
	iE-Extensions				ProtocolExtensionContainer { { HS-DSCHRequiredPowerValueInformation-For-CellPortion-Item-ExtIEs} }		OPTIONAL,
	...
}

HS-DSCHRequiredPowerValueInformation-For-CellPortion-Item-ExtIEs NBAP-PROTOCOL-EXTENSION ::= {
	...
}

HS-DSCHRequiredPowerValueInformation-For-CellPortionLCR ::= SEQUENCE (SIZE (1..maxNrOfCellPortionsPerCellLCR)) OF HS-DSCHRequiredPowerValueInformation-For-CellPortionLCR-Item

HS-DSCHRequiredPowerValueInformation-For-CellPortionLCR-Item ::= SEQUENCE{
	cellPortionLCRID				CellPortionLCRID,
	hS-DSCHRequiredPowerValue	HS-DSCHRequiredPower,
	iE-Extensions				ProtocolExtensionContainer { { HS-DSCHRequiredPowerValueInformation-For-CellPortionLCR-Item-ExtIEs} }		OPTIONAL,
	...
}

HS-DSCHRequiredPowerValueInformation-For-CellPortionLCR-Item-ExtIEs NBAP-PROTOCOL-EXTENSION ::= {
	...
}

HSDPA-Associated-PICH-Information  ::= CHOICE {
	hsdpa-PICH-Shared-with-PCH						HSDPA-PICH-Shared-with-PCH,
	hsdpa-PICH-notShared-with-PCH					HSDPA-PICH-notShared-with-PCH,
	...
}

HSDPA-PICH-Shared-with-PCH ::= SEQUENCE {
	hsdpa-PICH-SharedPCH-ID							CommonPhysicalChannelID,
	...
}

HSDPA-PICH-notShared-with-PCH ::= SEQUENCE {
	hSDPA-PICH-notShared-ID							CommonPhysicalChannelID,
	fdd-DL-Channelisation-CodeNumber				FDD-DL-ChannelisationCodeNumber,
	pich-Power										PICH-Power,
	pich-Mode										PICH-Mode,
	sttd-Indicator									STTD-Indicator,
	...
}

HSDSCH-Common-System-InformationFDD  ::= SEQUENCE {
	hsdsch-Common-Information						HSDSCH-Common-Information								OPTIONAL,
	commonMACFlow-Specific-Information				CommonMACFlow-Specific-InfoList							OPTIONAL,
	iE-Extensions									ProtocolExtensionContainer { { HSDSCH-Common-System-InformationFDD-ExtIEs } }		OPTIONAL,
	...
}

HSDSCH-Common-System-InformationFDD-ExtIEs NBAP-PROTOCOL-EXTENSION ::= {
	...
}

HSDSCH-Common-System-Information-ResponseFDD  ::= SEQUENCE {
	hsSCCH-Specific-Information-ResponseFDD			HSSCCH-Specific-InformationRespListFDD				OPTIONAL,
	hARQ-MemoryPartitioning							HARQ-MemoryPartitioning								OPTIONAL,
	commonMACFlow-Specific-Info-Response			CommonMACFlow-Specific-InfoList-Response			OPTIONAL,
	iE-Extensions									ProtocolExtensionContainer { { HSDSCH-Common-System-Information-ResponseFDD-ExtIEs } }		OPTIONAL,
	...
}

HSDSCH-Common-System-Information-ResponseFDD-ExtIEs NBAP-PROTOCOL-EXTENSION ::= {
	...
}

HSDSCH-Common-Information ::= SEQUENCE {
	cCCH-PriorityQueue-Id											PriorityQueue-Id,
	sRB1-PriorityQueue-Id											PriorityQueue-Id,
	associatedCommon-MACFlow										Common-MACFlow-ID,
	fACH-Measurement-Occasion-Cycle-Length-Coefficient				FACH-Measurement-Occasion-Cycle-Length-Coefficient				OPTIONAL,
	rACH-Measurement-Result											RACH-Measurement-Result,
	bCCH-Specific-HSDSCH-RNTI-Information							BCCH-Specific-HSDSCH-RNTI-Information,
	iE-Extensions						ProtocolExtensionContainer { { HSDSCH-Common-Information-ExtIEs} }		OPTIONAL,
	...
}

HSDSCH-Common-Information-ExtIEs NBAP-PROTOCOL-EXTENSION ::= {
	...
}

HSDSCH-FDD-Information ::= SEQUENCE {
	hSDSCH-MACdFlows-Information				HSDSCH-MACdFlows-Information,
	ueCapability-Info							UE-Capability-Information,
	mAChs-Reordering-Buffer-Size-for-RLC-UM		MAChsReorderingBufferSize-for-RLC-UM,
	cqiFeedback-CycleK							CQI-Feedback-Cycle,
	cqiRepetitionFactor							CQI-RepetitionFactor						OPTIONAL,
	-- This IE shall be present if the CQI Feedback Cycle k is greater than 0
	ackNackRepetitionFactor						AckNack-RepetitionFactor,
	cqiPowerOffset								CQI-Power-Offset,
	ackPowerOffset								Ack-Power-Offset,
	nackPowerOffset								Nack-Power-Offset,
	hsscch-PowerOffset							HSSCCH-PowerOffset							OPTIONAL,
	measurement-Power-Offset					Measurement-Power-Offset					OPTIONAL,
	iE-Extensions								ProtocolExtensionContainer { { HSDSCH-FDD-Information-ExtIEs} }		OPTIONAL,
	...
}

HSDSCH-FDD-Information-ExtIEs NBAP-PROTOCOL-EXTENSION ::= {
	{ ID id-HARQ-Preamble-Mode 						CRITICALITY ignore		EXTENSION	HARQ-Preamble-Mode				PRESENCE optional}|
	{ ID id-MIMO-ActivationIndicator				CRITICALITY reject		EXTENSION	MIMO-ActivationIndicator				PRESENCE optional}|
	{ ID id-HSDSCH-MACdPDUSizeFormat 				CRITICALITY reject		EXTENSION	HSDSCH-MACdPDUSizeFormat				PRESENCE optional}|
	{ ID id-SixtyfourQAM-UsageAllowedIndicator		CRITICALITY ignore		EXTENSION	SixtyfourQAM-UsageAllowedIndicator	PRESENCE optional}|
	{ ID id-UE-with-enhanced-HS-SCCH-support-indicator	CRITICALITY ignore		EXTENSION	NULL					PRESENCE optional}|
	{ ID id-EnhancedHSServingCC-Abort				CRITICALITY reject		EXTENSION	EnhancedHSServingCC-Abort				PRESENCE optional}|
	{ ID id-UE-SupportIndicatorExtension			CRITICALITY ignore		EXTENSION	UE-SupportIndicatorExtension			PRESENCE optional}|
	{ ID id-Single-Stream-MIMO-ActivationIndicator	CRITICALITY reject		EXTENSION	Single-Stream-MIMO-ActivationIndicator		PRESENCE optional},
	...
}

HSDSCH-TDD-Information ::= SEQUENCE {
	hSDSCH-MACdFlows-Information				HSDSCH-MACdFlows-Information,
	ueCapability-Info							UE-Capability-Information,
	mAChs-Reordering-Buffer-Size-for-RLC-UM		MAChsReorderingBufferSize-for-RLC-UM,
	tDD-AckNack-Power-Offset					TDD-AckNack-Power-Offset,
	iE-Extensions								ProtocolExtensionContainer { { HSDSCH-TDD-Information-ExtIEs} }		OPTIONAL,
	...
}

HSDSCH-TDD-Information-ExtIEs NBAP-PROTOCOL-EXTENSION ::= {
	{ ID id-HSSICH-SIRTarget		CRITICALITY	ignore			EXTENSION 	UL-SIR 					PRESENCE 	optional}|
 -- Applicable to 1.28Mcps TDD only
	{ ID id-HSSICH-TPC-StepSize		CRITICALITY	ignore			EXTENSION 	TDD-TPC-UplinkStepSize-LCR	PRESENCE 	optional}|
	 -- Applicable to 1.28Mcps TDD only
	{ ID id-HSDSCH-MACdPDUSizeFormat 	CRITICALITY reject		EXTENSION	HSDSCH-MACdPDUSizeFormat 	PRESENCE optional}|
	{ ID id-tSN-Length				CRITICALITY reject			EXTENSION  TSN-Length				PRESENCE optional }|
	-- Applicable for 1.28Mcps TDD when using multiple frequencies
		{ ID id-MIMO-ActivationIndicator				CRITICALITY reject		EXTENSION	MIMO-ActivationIndicator				PRESENCE optional},
...
}


HSDSCH-Information-to-Modify ::= SEQUENCE {
	hsDSCH-MACdFlow-Specific-Info-to-Modify			HSDSCH-MACdFlow-Specific-InfoList-to-Modify		OPTIONAL,
	priorityQueueInfotoModify						PriorityQueue-InfoList-to-Modify				OPTIONAL,
	mAChs-Reordering-Buffer-Size-for-RLC-UM			MAChsReorderingBufferSize-for-RLC-UM			OPTIONAL,
	cqiFeedback-CycleK								CQI-Feedback-Cycle								OPTIONAL,	-- For FDD only
	cqiRepetitionFactor								CQI-RepetitionFactor							OPTIONAL,	-- For FDD only
	ackNackRepetitionFactor							AckNack-RepetitionFactor						OPTIONAL,	-- For FDD only
	cqiPowerOffset									CQI-Power-Offset								OPTIONAL,	-- For FDD only
	ackPowerOffset									Ack-Power-Offset								OPTIONAL,	-- For FDD only
	nackPowerOffset									Nack-Power-Offset								OPTIONAL,	-- For FDD only
	hsscch-PowerOffset								HSSCCH-PowerOffset								OPTIONAL,	-- For FDD only
	measurement-Power-Offset						Measurement-Power-Offset						OPTIONAL,	-- For FDD only
	hSSCCHCodeChangeGrant							HSSCCH-Code-Change-Grant						OPTIONAL,
	tDDAckNackPowerOffset							TDD-AckNack-Power-Offset						OPTIONAL,	-- For TDD only
	iE-Extensions									ProtocolExtensionContainer { { HSDSCH-Information-to-Modify-ExtIEs} }		OPTIONAL,
	...
}

HSDSCH-Information-to-Modify-ExtIEs NBAP-PROTOCOL-EXTENSION ::= {
	{ ID id-HARQ-Preamble-Mode					CRITICALITY ignore		EXTENSION	HARQ-Preamble-Mode	PRESENCE optional}|
	{ ID id-HSSICH-SIRTarget					CRITICALITY	ignore		EXTENSION	UL-SIR			PRESENCE optional}|
	 -- Applicable to 1.28Mcps TDD only
	{ ID id-ueCapability-Info					CRITICALITY	ignore		EXTENSION	UE-Capability-Information	PRESENCE optional}|
	{ ID id-HSSICH-TPC-StepSize					CRITICALITY	ignore		EXTENSION 	TDD-TPC-UplinkStepSize-LCR	PRESENCE optional}|
	 -- Applicable to 1.28Mcps TDD only
	{ ID id-HS-PDSCH-Code-Change-Grant			CRITICALITY	ignore		EXTENSION	HS-PDSCH-Code-Change-Grant	PRESENCE optional}|
	 -- Applicable to FDD only
	{ ID id-MIMO-Mode-Indicator					CRITICALITY reject		EXTENSION 	MIMO-Mode-Indicator	PRESENCE optional }|
	{ ID id-HSDSCH-MACdPDUSizeFormat			CRITICALITY reject		EXTENSION	HSDSCH-MACdPDUSizeFormat 	PRESENCE optional}|
	{ ID id-SixtyfourQAM-UsageAllowedIndicator	CRITICALITY ignore		EXTENSION 	SixtyfourQAM-UsageAllowedIndicator		PRESENCE optional}|
	{ ID id-EnhancedHSServingCC-Abort			CRITICALITY reject		EXTENSION	EnhancedHSServingCC-Abort			PRESENCE optional}|
	{ ID id-UE-SupportIndicatorExtension		CRITICALITY ignore		EXTENSION	UE-SupportIndicatorExtension		PRESENCE optional}|
	{ ID id-Single-Stream-MIMO-Mode-Indicator	CRITICALITY reject		EXTENSION 	Single-Stream-MIMO-Mode-Indicator	PRESENCE optional },
	 -- Applicable to FDD only
	...
}

HSDSCH-MACdFlow-Specific-InfoList-to-Modify ::= SEQUENCE (SIZE (1..maxNrOfMACdFlows)) OF HSDSCH-MACdFlow-Specific-InfoItem-to-Modify

HSDSCH-MACdFlow-Specific-InfoItem-to-Modify ::= SEQUENCE {
	hsDSCH-MACdFlow-ID					HSDSCH-MACdFlow-ID,
	allocationRetentionPriority			AllocationRetentionPriority					OPTIONAL,
	transportBearerRequestIndicator		TransportBearerRequestIndicator,
	bindingID							BindingID									OPTIONAL,
	transportLayerAddress				TransportLayerAddress						OPTIONAL,
	iE-Extensions						ProtocolExtensionContainer { { HSDSCH-MACdFlow-Specific-InfoItem-to-Modify-ExtIEs} }		OPTIONAL,
	...
}

HSDSCH-MACdFlow-Specific-InfoItem-to-Modify-ExtIEs NBAP-PROTOCOL-EXTENSION ::= {
	{ID	id-TnlQos			CRITICALITY ignore		EXTENSION TnlQos	PRESENCE optional},
	...
}

HSDSCH-MACdPDUSizeFormat ::= ENUMERATED {
	indexedMACdPDU-Size,
	flexibleMACdPDU-Size
}

HSDSCH-MACdPDU-SizeCapability ::= ENUMERATED {
	indexedSizeCapable,
	flexibleSizeCapable
}

HSDSCH-Information-to-Modify-Unsynchronised ::= SEQUENCE {
	hsDSCH-MACdFlow-Specific-Info-to-Modify			HSDSCH-MACdFlow-Specific-InfoList-to-Modify		OPTIONAL,
	priorityQueueInfotoModifyUnsynchronised			PriorityQueue-InfoList-to-Modify-Unsynchronised	OPTIONAL,
	cqiPowerOffset									CQI-Power-Offset								OPTIONAL,	-- For FDD only
	ackPowerOffset									Ack-Power-Offset								OPTIONAL,	-- For FDD only
	nackPowerOffset									Nack-Power-Offset								OPTIONAL,	-- For FDD only
	hsscch-PowerOffset								HSSCCH-PowerOffset								OPTIONAL,	-- For FDD only
	tDDAckNackPowerOffset							TDD-AckNack-Power-Offset						OPTIONAL,	-- For TDD only
	iE-Extensions									ProtocolExtensionContainer { { HSDSCH-Information-to-Modify-Unsynchronised-ExtIEs} }		OPTIONAL,
	...
}

HSDSCH-Information-to-Modify-Unsynchronised-ExtIEs NBAP-PROTOCOL-EXTENSION ::= {
	{ ID id-HARQ-Preamble-Mode					CRITICALITY ignore		EXTENSION	HARQ-Preamble-Mode	PRESENCE optional}|
	{ ID id-HSSICH-SIRTarget					CRITICALITY	ignore		EXTENSION	UL-SIR			PRESENCE optional}|
	 -- Applicable to 1.28Mcps TDD only
	{ ID id-ueCapability-Info					CRITICALITY	ignore		EXTENSION	UE-Capability-Information	PRESENCE optional}|
	{ ID id-HSSICH-TPC-StepSize					CRITICALITY	ignore		EXTENSION 	TDD-TPC-UplinkStepSize-LCR	PRESENCE optional}|
	 -- Applicable to 1.28Mcps TDD only
	{ ID id-MIMO-Mode-Indicator					CRITICALITY reject		EXTENSION MIMO-Mode-Indicator	PRESENCE	optional }|
	{ ID id-SixtyfourQAM-UsageAllowedIndicator	CRITICALITY ignore		EXTENSION 	SixtyfourQAM-UsageAllowedIndicator		PRESENCE optional}|
	{ ID id-EnhancedHSServingCC-Abort			CRITICALITY reject		EXTENSION	EnhancedHSServingCC-Abort			PRESENCE optional}|
	{ ID id-UE-SupportIndicatorExtension		CRITICALITY ignore		EXTENSION	UE-SupportIndicatorExtension		PRESENCE optional}|
	{ ID id-Single-Stream-MIMO-Mode-Indicator	CRITICALITY reject		EXTENSION 	Single-Stream-MIMO-Mode-Indicator	PRESENCE optional },
	 -- Applicable to FDD only
	...
}

HSDSCH-FDD-Information-Response ::= SEQUENCE {
	hsDSCH-MACdFlow-Specific-InformationResp		HSDSCH-MACdFlow-Specific-InformationResp							OPTIONAL,
	hsSCCH-Specific-Information-ResponseFDD			HSSCCH-Specific-InformationRespListFDD								OPTIONAL,
	hARQ-MemoryPartitioning							HARQ-MemoryPartitioning												OPTIONAL,
	iE-Extensions									ProtocolExtensionContainer { { HSDSCH-FDD-Information-Response-ExtIEs } }		OPTIONAL,
	...
}

HSDSCH-FDD-Information-Response-ExtIEs NBAP-PROTOCOL-EXTENSION ::= {
{	ID id-HARQ-Preamble-Mode-Activation-Indicator		CRITICALITY	ignore	EXTENSION	HARQ-Preamble-Mode-Activation-Indicator						PRESENCE	optional}|
	{ ID id-MIMO-N-M-Ratio								CRITICALITY	ignore	EXTENSION	MIMO-N-M-Ratio										PRESENCE optional}|
	{ ID id-SixtyfourQAM-DL-UsageIndicator				CRITICALITY ignore	EXTENSION SixtyfourQAM-DL-UsageIndicator		PRESENCE optional }|
	{ ID id-HSDSCH-TBSizeTableIndicator					CRITICALITY ignore	EXTENSION HSDSCH-TBSizeTableIndicator			PRESENCE optional },
	...
}

HS-DSCH-FDD-Secondary-Serving-Information ::= SEQUENCE {
	hsscch-PowerOffset						HSSCCH-PowerOffset							OPTIONAL,
	measurement-Power-Offset				Measurement-Power-Offset,
	sixtyfourQAM-UsageAllowedIndicator		SixtyfourQAM-UsageAllowedIndicator			OPTIONAL,
	hSDSCH-RNTI								HSDSCH-RNTI,
	iE-Extensions							ProtocolExtensionContainer { { HS-DSCH-FDD-Secondary-Serving-Information-ExtIEs } }		OPTIONAL,
	...
}

HS-DSCH-FDD-Secondary-Serving-Information-ExtIEs NBAP-PROTOCOL-EXTENSION ::= {
	{ID	id-MIMO-ActivationIndicator			CRITICALITY reject		EXTENSION MIMO-ActivationIndicator	PRESENCE optional}|
	{ID id-Single-Stream-MIMO-ActivationIndicator	CRITICALITY reject		EXTENSION	Single-Stream-MIMO-ActivationIndicator		PRESENCE optional}|
	{ID	id-DiversityMode			CRITICALITY reject		EXTENSION DiversityMode	PRESENCE optional}|
	{ID	id-TransmitDiversityIndicator			CRITICALITY reject		EXTENSION TransmitDiversityIndicator	PRESENCE optional},
	...
}

HS-DSCH-FDD-Secondary-Serving-Information-Response ::= SEQUENCE {
	hsSCCH-Specific-Information-ResponseFDD		HSSCCH-Specific-InformationRespListFDD					OPTIONAL,
	sixtyfourQAM-DL-UsageIndicator				SixtyfourQAM-DL-UsageIndicator							OPTIONAL,
	hSDSCH-TBSizeTableIndicator					HSDSCH-TBSizeTableIndicator								OPTIONAL,
	iE-Extensions					ProtocolExtensionContainer { { HS-DSCH-FDD-Secondary-Serving-Information-Respons-ExtIEs } }			OPTIONAL,
	...
}

HS-DSCH-FDD-Secondary-Serving-Information-Respons-ExtIEs NBAP-PROTOCOL-EXTENSION ::= {
	{ID	id-MIMO-N-M-Ratio			CRITICALITY ignore		EXTENSION MIMO-N-M-Ratio			PRESENCE optional},
	...
}

HS-DSCH-Secondary-Serving-Information-To-Modify ::= SEQUENCE {
	hsscch-PowerOffset							HSSCCH-PowerOffset									OPTIONAL,
	measurement-Power-Offset					Measurement-Power-Offset							OPTIONAL,
	hSSCCH-CodeChangeGrant						HSSCCH-Code-Change-Grant							OPTIONAL,
	sixtyfourQAM-UsageAllowedIndicator			SixtyfourQAM-UsageAllowedIndicator					OPTIONAL,
	iE-Extensions								ProtocolExtensionContainer { { HS-DSCH-Secondary-Serving-Information-To-Modify-ExtIEs } }		OPTIONAL,
	...
}

HS-DSCH-Secondary-Serving-Information-To-Modify-ExtIEs NBAP-PROTOCOL-EXTENSION ::= {
	{ID	id-MIMO-Mode-Indicator			CRITICALITY reject		EXTENSION MIMO-Mode-Indicator		PRESENCE optional }|
	{ID id-Single-Stream-MIMO-Mode-Indicator	CRITICALITY reject		EXTENSION 	Single-Stream-MIMO-Mode-Indicator	PRESENCE optional }|
	{ID	id-DiversityMode		CRITICALITY reject		EXTENSION DiversityMode	PRESENCE optional}|
	{ID	id-TransmitDiversityIndicator			CRITICALITY reject		EXTENSION TransmitDiversityIndicator	PRESENCE optional}|
-- This IE shall be present if Diversity Mode IE is present and is not set to "none"
	{ID	id-NonCellSpecificTxDiversity			CRITICALITY reject		EXTENSION NonCellSpecificTxDiversity	PRESENCE optional},
	...
}

HS-DSCH-FDD-Secondary-Serving-Information-To-Modify-Unsynchronised ::= SEQUENCE {
	hsscch-PowerOffset							HSSCCH-PowerOffset									OPTIONAL,
	sixtyfourQAM-UsageAllowedIndicator			SixtyfourQAM-UsageAllowedIndicator					OPTIONAL,
	iE-Extensions			ProtocolExtensionContainer { { HS-DSCH-FDD-Secondary-Serving-Information-To-Modify-Unsynchronised-ExtIEs } }			OPTIONAL,
	...
}

HS-DSCH-FDD-Secondary-Serving-Information-To-Modify-Unsynchronised-ExtIEs NBAP-PROTOCOL-EXTENSION ::= {
	{ID	id-MIMO-Mode-Indicator					CRITICALITY reject		EXTENSION MIMO-Mode-Indicator						PRESENCE optional }|
	{ID id-Single-Stream-MIMO-Mode-Indicator	CRITICALITY reject		EXTENSION Single-Stream-MIMO-Mode-Indicator		PRESENCE optional },
	...
}

HS-DSCH-FDD-Secondary-Serving-Update-Information ::= SEQUENCE {
	hsSCCHCodeChangeIndicator					HSSCCH-CodeChangeIndicator					OPTIONAL,
	hS-PDSCH-Code-Change-Indicator				HS-PDSCH-Code-Change-Indicator				OPTIONAL,
	-- This IE shall never be included. If received it shall be ignored.
	iE-Extensions								ProtocolExtensionContainer { { HS-DSCH-FDD-Secondary-Serving-Update-Information-ExtIEs } }		OPTIONAL,
	...
}

HS-DSCH-FDD-Secondary-Serving-Update-Information-ExtIEs NBAP-PROTOCOL-EXTENSION ::= {
	...
}

HS-DSCH-Secondary-Serving-Cell-Change-Information-Response ::= SEQUENCE {
	hS-DSCH-Secondary-Serving-cell-choice		HS-DSCH-Secondary-Serving-cell-change-choice,
	iE-Extensions								ProtocolExtensionContainer { { HS-DSCH-Secondary-Serving-Cell-Change-Information-Response-ExtIEs } }		OPTIONAL,
	...
}

HS-DSCH-Secondary-Serving-Cell-Change-Information-Response-ExtIEs NBAP-PROTOCOL-EXTENSION ::= {
	...
}

HS-DSCH-Secondary-Serving-cell-change-choice ::= CHOICE {
	hS-Secondary-Serving-cell-change-successful			HS-Secondary-Serving-cell-change-successful,
	hS-Secondary-Serving-cell-change-unsuccessful		HS-Secondary-Serving-cell-change-unsuccessful,
	...
}

HS-Secondary-Serving-cell-change-successful ::= SEQUENCE {
	hS-DSCH-FDD-Secondary-Serving-Information-Response		HS-DSCH-FDD-Secondary-Serving-Information-Response,
	iE-Extensions						ProtocolExtensionContainer { { HS-Secondary-Serving-cell-change-successful-ExtIEs} } OPTIONAL,
	...
}

HS-Secondary-Serving-cell-change-successful-ExtIEs NBAP-PROTOCOL-EXTENSION ::= {
	...
}

HS-Secondary-Serving-cell-change-unsuccessful ::= SEQUENCE {
	cause							Cause,
	iE-Extensions					ProtocolExtensionContainer { { HS-Secondary-Serving-cell-change-unsuccessful-ExtIEs} } OPTIONAL,
	...
}

HS-Secondary-Serving-cell-change-unsuccessful-ExtIEs NBAP-PROTOCOL-EXTENSION ::= {
	...
}
HS-DSCH-Secondary-Serving-Remove ::= NULL


HSDSCH-Paging-System-InformationFDD  ::= SEQUENCE {
	paging-MACFlow-Specific-Information				Paging-MACFlow-Specific-Information,
	hSSCCH-Power									DL-Power,
	hSPDSCH-Power									DL-Power,
	number-of-PCCH-transmission						Number-of-PCCH-transmission,
	transport-Block-Size-List						Transport-Block-Size-List,
	iE-Extensions									ProtocolExtensionContainer { { HSDSCH-Paging-System-InformationFDD-ExtIEs } }		OPTIONAL,
	...
}

HSDSCH-Paging-System-InformationFDD-ExtIEs NBAP-PROTOCOL-EXTENSION ::= {
	...
}

HSDSCH-Paging-System-Information-ResponseFDD ::= SEQUENCE (SIZE (1..maxNrOfPagingMACFlow)) OF HSDSCH-Paging-System-Information-ResponseList

HSDSCH-Paging-System-Information-ResponseList  ::= SEQUENCE {
	pagingMACFlow-ID								Paging-MACFlow-ID,
	bindingID										BindingID									OPTIONAL,
	transportLayerAddress							TransportLayerAddress						OPTIONAL,
	hSPDSCH-Code-Index								HSPDSCH-Code-Index,
	iE-Extensions									ProtocolExtensionContainer { { HSDSCH-Paging-System-Information-ResponseList-ExtIEs } }		OPTIONAL,
	...
}

HSDSCH-Paging-System-Information-ResponseList-ExtIEs NBAP-PROTOCOL-EXTENSION ::= {
	...
}

HSDSCH-TDD-Information-Response ::= SEQUENCE {
	hsDSCH-MACdFlow-Specific-InformationResp		HSDSCH-MACdFlow-Specific-InformationResp	OPTIONAL,
	hsSCCH-Specific-Information-ResponseTDD			HSSCCH-Specific-InformationRespListTDD		OPTIONAL, -- Not Applicable to 1.28Mcps TDD or 7.68Mcps TDD
	hsSCCH-Specific-Information-ResponseTDDLCR		HSSCCH-Specific-InformationRespListTDDLCR	OPTIONAL, -- Not Applicable to 3.84Mcps TDD or 7.68Mcps TDD,This HSSCCH Specific Information is for the first Frequency repetition, HSSCCH Specific Information for Frequency repetitions 2 and on, should be defined in MultipleFreq-HSPDSCH-InformationList-ResponseTDDLCR
	hARQ-MemoryPartitioning							HARQ-MemoryPartitioning						OPTIONAL, -- This HARQ Memory Partitioning Information is for the first Frequency repetition, HARQ Memory Partitioning Information for Frequency repetitions 2 and on, should be defined in MultipleFreq-HSPDSCH-InformationList-ResponseTDDLCR
	iE-Extensions									ProtocolExtensionContainer { { HSDSCH-TDD-Information-Response-ExtIEs } }		OPTIONAL,
	...
}

HSDSCH-TDD-Information-Response-ExtIEs NBAP-PROTOCOL-EXTENSION ::= {
	{ID id-hsSCCH-Specific-Information-ResponseTDD768 					CRITICALITY ignore	EXTENSION HSSCCH-Specific-InformationRespListTDD768	PRESENCE optional}|
{ ID id-UARFCNforNt														CRITICALITY ignore	EXTENSION UARFCN																PRESENCE optional}|
	-- Applicable to 1.28Mcps TDD when using multiple frequencies ,This is the UARFCN for the first Frequency repetition
{ ID id-multipleFreq-HSPDSCH-InformationList-ResponseTDDLCR				CRITICALITY ignore	EXTENSION MultipleFreq-HSPDSCH-InformationList-ResponseTDDLCR	PRESENCE optional }|
	-- Applicable to 1.28Mcps TDD when using multiple frequencies ,This MultipleFreq-HSPDSCH-InformationList-ResponseTDDLCR is the HS-SCCH and HARQ Memory Partitioning information for the 2nd and beyond HS-PDSCH frequencies.
{ ID id-multicarrier-number												CRITICALITY ignore	EXTENSION  Multicarrier-Number													PRESENCE optional }|
	-- Applicable for 1.28Mcps TDD when using multiple frequencies
	{ID id-MIMO-SFMode-For-HSPDSCHDualStream			CRITICALITY reject		EXTENSION MIMO-SFMode-For-HSPDSCHDualStream							PRESENCE optional}|
	{ID id-MIMO-ReferenceSignal-InformationListLCR		CRITICALITY reject	EXTENSION MIMO-ReferenceSignal-InformationListLCR		PRESENCE optional},
	...
}

HSDSCH-MACdFlow-Specific-InformationResp ::= SEQUENCE (SIZE (1..maxNrOfMACdFlows)) OF HSDSCH-MACdFlow-Specific-InformationResp-Item

HSDSCH-MACdFlow-Specific-InformationResp-Item ::= SEQUENCE {
	hsDSCHMacdFlow-Id								HSDSCH-MACdFlow-ID,
	bindingID										BindingID					OPTIONAL,
	transportLayerAddress							TransportLayerAddress		OPTIONAL,
	hSDSCH-Initial-Capacity-Allocation				HSDSCH-Initial-Capacity-Allocation OPTIONAL,
	iE-Extensions									ProtocolExtensionContainer { { HSDSCH-MACdFlow-Specific-InformationRespItem-ExtIEs } }		OPTIONAL,
	...
}

HSDSCH-MACdFlow-Specific-InformationRespItem-ExtIEs NBAP-PROTOCOL-EXTENSION ::= {
	...
}

HSDSCH-MACdFlows-Information ::= SEQUENCE {
	hSDSCH-MACdFlow-Specific-Info					HSDSCH-MACdFlow-Specific-InfoList,
	priorityQueue-Info								PriorityQueue-InfoList,
	iE-Extensions									ProtocolExtensionContainer { { HSDSCH-MACdFlows-Information-ExtIEs } }			OPTIONAL,
	...
}

HSDSCH-MACdFlows-Information-ExtIEs NBAP-PROTOCOL-EXTENSION ::= {
	...
}

HSDSCH-MACdFlow-Specific-InfoList ::= SEQUENCE (SIZE (1..maxNrOfMACdFlows)) OF HSDSCH-MACdFlow-Specific-InfoItem

HSDSCH-MACdFlow-Specific-InfoItem ::= SEQUENCE {
	hsDSCH-MACdFlow-ID					HSDSCH-MACdFlow-ID,
	allocationRetentionPriority			AllocationRetentionPriority,
	bindingID							BindingID					OPTIONAL,
	transportLayerAddress				TransportLayerAddress		OPTIONAL,
	iE-Extensions						ProtocolExtensionContainer { { HSDSCH-MACdFlow-Specific-InfoItem-ExtIEs} }		OPTIONAL,
	...
}

HSDSCH-MACdFlow-Specific-InfoItem-ExtIEs NBAP-PROTOCOL-EXTENSION ::= {
	{ID	id-TnlQos			CRITICALITY ignore		EXTENSION TnlQos	PRESENCE optional },
	...
}

HSDSCH-MACdFlows-to-Delete ::= SEQUENCE (SIZE (1..maxNrOfMACdFlows)) OF HSDSCH-MACdFlows-to-Delete-Item

HSDSCH-MACdFlows-to-Delete-Item ::= SEQUENCE {
	hsDSCH-MACdFlow-ID					HSDSCH-MACdFlow-ID,
	iE-Extensions						ProtocolExtensionContainer { { HSDSCH-MACdFlows-to-Delete-Item-ExtIEs} }		OPTIONAL,
	...
}

HSDSCH-MACdFlows-to-Delete-Item-ExtIEs NBAP-PROTOCOL-EXTENSION ::= {
	...
}

HSDSCH-TBSizeTableIndicator ::= ENUMERATED {
	octet-aligned
}

HSSCCH-PowerOffset ::= INTEGER (0..255)
-- PowerOffset = -32 + offset * 0.25
-- Unit dB, Range -32dB .. +31.75dB, Step +0.25dB

HSDSCH-Initial-Capacity-Allocation::= SEQUENCE (SIZE (1..maxNrOfPriorityQueues)) OF HSDSCH-Initial-Capacity-AllocationItem

HSDSCH-Initial-Capacity-AllocationItem ::= SEQUENCE {
	schedulingPriorityIndicator		SchedulingPriorityIndicator,
	maximum-MACdPDU-Size			MACdPDU-Size,
	hSDSCH-InitialWindowSize		HSDSCH-InitialWindowSize,
	iE-Extensions					ProtocolExtensionContainer { { HSDSCH-Initial-Capacity-AllocationItem-ExtIEs } } OPTIONAL,
	...
}

HSDSCH-Initial-Capacity-AllocationItem-ExtIEs NBAP-PROTOCOL-EXTENSION ::= {
	{ ID id-MaximumMACdPDU-SizeExtended 	CRITICALITY ignore		EXTENSION	MAC-PDU-SizeExtended	PRESENCE optional},
	...
}

HSDSCH-InitialWindowSize			::= INTEGER (1..255)
-- Number of MAC-d PDUs.


HSDSCH-PreconfigurationInfo ::= SEQUENCE {
	setsOfHS-SCCH-Codes		SetsOfHS-SCCH-Codes,
	hARQ-MemoryPartitioning		HARQ-MemoryPartitioning,
	e-DCH-FDD-DL-Control-Channel-Information		E-DCH-FDD-DL-Control-Channel-Information		OPTIONAL,
	hARQ-Preamble-Mode-Activation-Indicator		HARQ-Preamble-Mode-Activation-Indicator		OPTIONAL,
	mIMO-N-M-Ratio			MIMO-N-M-Ratio		OPTIONAL,
	continuousPacketConnectivityHS-SCCH-less-Information-Response	ContinuousPacketConnectivityHS-SCCH-less-Information-Response		OPTIONAL,
	iE-Extensions						ProtocolExtensionContainer { { HSDSCH-PreconfigurationInfo-ExtIEs} }		OPTIONAL,
	...
}

HSDSCH-PreconfigurationInfo-ExtIEs NBAP-PROTOCOL-EXTENSION ::= {
	{ ID id-Additional-EDCH-Preconfiguration-Information	CRITICALITY ignore	EXTENSION Additional-EDCH-Preconfiguration-Information			PRESENCE optional },
	...
}

Additional-EDCH-Preconfiguration-Information	::= SEQUENCE (SIZE (1..maxNrOfEDCH-1)) OF Additional-EDCH-Preconfiguration-Information-ItemIEs

Additional-EDCH-Preconfiguration-Information-ItemIEs	::= SEQUENCE {
	e-DCH-FDD-DL-Control-Channel-Information		E-DCH-FDD-DL-Control-Channel-Information,
	iE-Extensions					ProtocolExtensionContainer { { Additional-EDCH-Preconfiguration-Information-ItemIEs-ExtIEs} } OPTIONAL,
	...
}

Additional-EDCH-Preconfiguration-Information-ItemIEs-ExtIEs	NBAP-PROTOCOL-EXTENSION ::= {
	...
}

HSDSCH-PreconfigurationSetup ::= SEQUENCE {
	mAChsResetScheme		MAChsResetScheme,
	hSDSCH-Physical-Layer-Category		INTEGER (1..64,...),
	mAChs-Reordering-Buffer-Size-for-RLC-UM		MAChsReorderingBufferSize-for-RLC-UM,
	secondaryServingCells		SecondaryServingCells			OPTIONAL,
	numPrimaryHS-SCCH-Codes		NumHS-SCCH-Codes			OPTIONAL,
	hARQ-Preamble-Mode		HARQ-Preamble-Mode						OPTIONAL,
	mIMO-ActivationIndicator		MIMO-ActivationIndicator			OPTIONAL,
	hSDSCH-MACdPDUSizeFormat		HSDSCH-MACdPDUSizeFormat			OPTIONAL,
	sixtyfourQAM-UsageAllowedIndicator		SixtyfourQAM-UsageAllowedIndicator			OPTIONAL,
	uE-with-enhanced-HS-SCCH-support-indicator		NULL		OPTIONAL,
	continuousPacketConnectivityHS-SCCH-less-Information			ContinuousPacketConnectivityHS-SCCH-less-Information		OPTIONAL,
	iE-Extensions						ProtocolExtensionContainer { { HSDSCHPreconfigurationSetup-ExtIEs } }			OPTIONAL,
	...
}

HSDSCHPreconfigurationSetup-ExtIEs NBAP-PROTOCOL-EXTENSION ::= {
	{ID id-UE-SupportIndicatorExtension		CRITICALITY ignore		EXTENSION	UE-SupportIndicatorExtension	PRESENCE optional},
	...
}


HS-SCCH-PreconfiguredCodes				::= SEQUENCE (SIZE (1..maxNrOfHSSCCHCodes)) OF HS-SCCH-PreconfiguredCodesItem

HS-SCCH-PreconfiguredCodesItem ::= SEQUENCE {
	hS-SCCH-CodeNumber			HS-SCCH-CodeNumber,
	iE-Extensions			ProtocolExtensionContainer { { HS-SCCH-PreconfiguredCodesItem-ExtIEs} } OPTIONAL,
	...
}

HS-SCCH-PreconfiguredCodesItem-ExtIEs NBAP-PROTOCOL-EXTENSION ::= {
	...
}

HS-SCCH-CodeNumber ::= INTEGER (0..127)


HSSCCH-Specific-InformationRespListFDD ::= SEQUENCE (SIZE (1..maxNrOfHSSCCHCodes)) OF HSSCCH-Codes

HSSCCH-Codes ::= SEQUENCE {
	codeNumber										INTEGER (0..127),
	iE-Extensions									ProtocolExtensionContainer { { HSSCCH-Specific-InformationRespItemFDD-ExtIEs } }		OPTIONAL,
	...
}

HSSCCH-Specific-InformationRespItemFDD-ExtIEs NBAP-PROTOCOL-EXTENSION ::= {
	...
}

HSSCCH-Specific-InformationRespListTDD ::= SEQUENCE (SIZE (1..maxNrOfHSSCCHCodes)) OF HSSCCH-Specific-InformationRespItemTDD

HSSCCH-Specific-InformationRespItemTDD ::= SEQUENCE {
	timeslot										TimeSlot,
	midambleShiftAndBurstType						MidambleShiftAndBurstType,
	tDD-ChannelisationCode							TDD-ChannelisationCode,
	hSSICH-Info										HSSICH-Info,
	iE-Extensions									ProtocolExtensionContainer { { HSSCCH-Specific-InformationRespItemTDD-ExtIEs } }			OPTIONAL,
	...
}

HSSCCH-Specific-InformationRespItemTDD-ExtIEs NBAP-PROTOCOL-EXTENSION ::= {
	...
}

HSSCCH-Specific-InformationRespListTDDLCR ::= SEQUENCE (SIZE (1..maxNrOfHSSCCHCodes)) OF HSSCCH-Specific-InformationRespItemTDDLCR

HSSCCH-Specific-InformationRespItemTDDLCR ::= SEQUENCE {
	timeslotLCR									TimeSlotLCR,
	midambleShiftLCR							MidambleShiftLCR,
	first-TDD-ChannelisationCode					TDD-ChannelisationCode,
	second-TDD-ChannelisationCode			TDD-ChannelisationCode,
	hSSICH-InfoLCR								HSSICH-InfoLCR,
	iE-Extensions								ProtocolExtensionContainer { { HSSCCH-Specific-InformationRespItemTDDLCR-ExtIEs } }			OPTIONAL,
	...
}

HSSCCH-Specific-InformationRespItemTDDLCR-ExtIEs NBAP-PROTOCOL-EXTENSION ::= {
	{ID id-UARFCNforNt		CRITICALITY reject		EXTENSION UARFCN		PRESENCE optional},
	-- Applicable for 1.28Mcps TDD when using multiple frequencies. this IE indicates the frequency which is actually used by the  HS-SCCH
	...
}
HSSCCH-Specific-InformationRespListTDD768 ::= SEQUENCE (SIZE (1..maxNrOfHSSCCHCodes)) OF HSSCCH-Specific-InformationRespItemTDD768

HSSCCH-Specific-InformationRespItemTDD768 ::= SEQUENCE {
	timeslot										TimeSlot,
	midambleShiftAndBurstType768					MidambleShiftAndBurstType768,
	tDD-ChannelisationCode768						TDD-ChannelisationCode768,
	hSSICH-Info768									HSSICH-Info768,
	iE-Extensions									ProtocolExtensionContainer { { HSSCCH-Specific-InformationRespItemTDD768-ExtIEs } }			OPTIONAL,
	...
}

HSSCCH-Specific-InformationRespItemTDD768-ExtIEs NBAP-PROTOCOL-EXTENSION ::= {
	...
}


HSSICH-Info ::= SEQUENCE {
	hsSICH-ID										HS-SICH-ID,
	timeslot										TimeSlot,
	midambleShiftAndBurstType						MidambleShiftAndBurstType,
	tDD-ChannelisationCode							TDD-ChannelisationCode,
	iE-Extensions									ProtocolExtensionContainer { { HSSICH-Info-ExtIEs } }			OPTIONAL,
	...
}

HSSICH-Info-ExtIEs NBAP-PROTOCOL-EXTENSION ::= {
	...
}

HSSICH-InfoLCR ::= SEQUENCE {
	hsSICH-ID										HS-SICH-ID,
	timeslotLCR										TimeSlotLCR,
	midambleShiftLCR								MidambleShiftLCR,
	tDD-ChannelisationCode						TDD-ChannelisationCode,
	iE-Extensions									ProtocolExtensionContainer { { HSSICH-Info-LCR-ExtIEs } }			OPTIONAL,
	...
}

HSSICH-Info-LCR-ExtIEs NBAP-PROTOCOL-EXTENSION ::= {
	{ ID id-Extended-HS-SICH-ID							CRITICALITY ignore	EXTENSION Extended-HS-SICH-ID	PRESENCE optional},
	-- used if the HS-SICH identity has a value larger than 31
	...
}

HSSICH-Info768 ::= SEQUENCE {
	hsSICH-ID										HS-SICH-ID,
	timeslot										TimeSlot,
	midambleShiftAndBurstType768					MidambleShiftAndBurstType768,
	tDD-ChannelisationCode768						TDD-ChannelisationCode768,
	iE-Extensions									ProtocolExtensionContainer { { HSSICH-Info-768-ExtIEs } }			OPTIONAL,
	...
}

HSSICH-Info-768-ExtIEs NBAP-PROTOCOL-EXTENSION ::= {
	...
}


HS-SICH-Reception-Quality-Value ::= SEQUENCE {
	failed-HS-SICH				HS-SICH-failed,
	missed-HS-SICH				HS-SICH-missed,
	total-HS-SICH				HS-SICH-total,
	iE-Extensions				ProtocolExtensionContainer { { HS-SICH-Reception-Quality-Value-ExtIEs} } OPTIONAL,
...
}

HS-SICH-Reception-Quality-Value-ExtIEs NBAP-PROTOCOL-EXTENSION ::= {
	{ ID id-Additional-failed-HS-SICH		CRITICALITY reject		EXTENSION 	HS-SICH-failed			PRESENCE 	optional	}|
	-- Mandatory for 1.28Mcps TDD only, used when there are more than 20 failed HS-SICH
	{ID id-Additional-missed-HS-SICH		CRITICALITY reject		EXTENSION 	HS-SICH-missed			PRESENCE	optional}|
	-- Mandatory for 1.28Mcps TDD only, used when there are more than 20 missed HS-SICH
	{ID id-Additional-total-HS-SICH			CRITICALITY reject		EXTENSION 	HS-SICH-total			PRESENCE	optional},
	-- Mandatory for 1.28Mcps TDD only, used when there are more than 20 total HS-SICH
	...
}

HS-SICH-failed ::= INTEGER (0..20)

HS-SICH-missed ::= INTEGER (0..20)

HS-SICH-total ::= INTEGER (0..20)

HS-SICH-Reception-Quality-Measurement-Value ::= INTEGER (0..20)
-- According to mapping in [23]

HSDSCH-MACdFlow-ID ::= INTEGER (0..maxNrOfMACdFlows-1)

HSDSCH-RNTI ::= INTEGER (0..65535)

HS-PDSCH-FDD-Code-Information ::= SEQUENCE {
	number-of-HS-PDSCH-codes						INTEGER (0..maxHS-PDSCHCodeNrComp-1),
	hS-PDSCH-Start-code-number 					HS-PDSCH-Start-code-number		OPTIONAL,
-- Only included when number of HS-DSCH codes > 0
	iE-Extensions				ProtocolExtensionContainer { { HS-PDSCH-FDD-Code-Information-ExtIEs} } OPTIONAL,
	...
}

HS-PDSCH-FDD-Code-Information-ExtIEs NBAP-PROTOCOL-EXTENSION ::= {
	...
}

HS-PDSCH-Start-code-number ::=	INTEGER (1..maxHS-PDSCHCodeNrComp-1)

HS-SCCH-ID ::= INTEGER (0..31)
HS-SICH-ID ::= INTEGER (0..31)

HS-SCCH-FDD-Code-Information::= CHOICE {
	replace					HS-SCCH-FDD-Code-List,
	remove					NULL,
	...
}

HS-SCCH-FDD-Code-List ::= SEQUENCE (SIZE (1..maxNrOfHSSCCHs)) OF HS-SCCH-FDD-Code-Information-Item

HS-SCCH-FDD-Code-Information-Item ::= INTEGER (0..maxHS-SCCHCodeNrComp-1)

HSSCCH-CodeChangeIndicator	::= ENUMERATED {
	hsSCCHCodeChangeNeeded
}

HSSCCH-Code-Change-Grant	::= ENUMERATED {
	changeGranted
}

HS-PDSCH-Code-Change-Indicator	::= ENUMERATED {
	hsPDSCHCodeChangeNeeded
}

HS-PDSCH-Code-Change-Grant	::= ENUMERATED {
	changeGranted
}

HSDSCH-Configured-Indicator::= ENUMERATED {
	configured-HS-DSCH,
	no-configured-HS-DSCH
}

HS-DSCH-Serving-Cell-Change-Info ::= SEQUENCE {
	hspdsch-RL-ID					RL-ID,
	hSDSCH-FDD-Information			HSDSCH-FDD-Information	OPTIONAL,
	hsdsch-RNTI						HSDSCH-RNTI,
	iE-Extensions					ProtocolExtensionContainer { { HS-DSCH-Serving-Cell-Change-Info-ExtIEs} }	OPTIONAL,
	...
}

HS-DSCH-Serving-Cell-Change-Info-ExtIEs NBAP-PROTOCOL-EXTENSION ::= {
	{ ID id-ContinuousPacketConnectivityHS-SCCH-less-Information	CRITICALITY reject		EXTENSION ContinuousPacketConnectivityHS-SCCH-less-Information			PRESENCE optional },
	...
}

HS-DSCH-Serving-Cell-Change-Info-Response::= SEQUENCE {
	hS-DSCH-serving-cell-choice		HS-DSCH-serving-cell-choice,
	iE-Extensions					ProtocolExtensionContainer { { HS-DSCH-serving-cell-informationResponse-ExtIEs} } OPTIONAL,
	...
}

HS-DSCH-serving-cell-informationResponse-ExtIEs NBAP-PROTOCOL-EXTENSION ::= {
	...
}

HS-DSCH-serving-cell-choice ::= CHOICE {
	hS-serving-cell-change-successful		HS-serving-cell-change-successful,
	hS-serving-cell-change-unsuccessful		HS-serving-cell-change-unsuccessful,
	...
}

HS-serving-cell-change-successful ::= SEQUENCE {
	hSDSCH-FDD-Information-Response		HSDSCH-FDD-Information-Response,
	iE-Extensions						ProtocolExtensionContainer { { HS-serving-cell-change-successful-ExtIEs} } OPTIONAL,
	...
}

HS-serving-cell-change-successful-ExtIEs NBAP-PROTOCOL-EXTENSION ::= {
	{ ID id-ContinuousPacketConnectivityHS-SCCH-less-Information-Response	CRITICALITY ignore		EXTENSION ContinuousPacketConnectivityHS-SCCH-less-Information-Response			PRESENCE optional },
	...
}

HS-serving-cell-change-unsuccessful ::= SEQUENCE {
	cause							Cause,
	iE-Extensions					ProtocolExtensionContainer { { HS-serving-cell-change-unsuccessful-ExtIEs} } OPTIONAL,
	...
}

HS-serving-cell-change-unsuccessful-ExtIEs NBAP-PROTOCOL-EXTENSION ::= {
	...
}


HS-DSCH-DRX-Cycle-FACH ::= ENUMERATED {v4,v8,v16,v32,...}

HS-DSCH-RX-Burst-FACH::= ENUMERATED {v1,v2,v4,v8,v16,...}


HSDSCH-FDD-Update-Information ::= SEQUENCE {
	hsSCCHCodeChangeIndicator						HSSCCH-CodeChangeIndicator					OPTIONAL,
	cqiFeedback-CycleK								CQI-Feedback-Cycle							OPTIONAL,
	cqiRepetitionFactor								CQI-RepetitionFactor						OPTIONAL,
	ackNackRepetitionFactor							AckNack-RepetitionFactor					OPTIONAL,
	cqiPowerOffset									CQI-Power-Offset 							OPTIONAL,
	ackPowerOffset									Ack-Power-Offset							OPTIONAL,
	nackPowerOffset									Nack-Power-Offset							OPTIONAL,
	iE-Extensions									ProtocolExtensionContainer { { HSDSCH-FDD-Update-Information-ExtIEs } }		OPTIONAL,
	...
}

HSDSCH-FDD-Update-Information-ExtIEs NBAP-PROTOCOL-EXTENSION ::= {
	{ID	id-HS-PDSCH-Code-Change-Indicator		CRITICALITY	ignore		EXTENSION	HS-PDSCH-Code-Change-Indicator	PRESENCE optional },
	...
}

HSDSCH-TDD-Update-Information ::= SEQUENCE {
	hsSCCHCodeChangeIndicator						HSSCCH-CodeChangeIndicator					OPTIONAL,
	tDDAckNackPowerOffset							TDD-AckNack-Power-Offset					OPTIONAL,
	iE-Extensions									ProtocolExtensionContainer { { HSDSCH-TDD-Update-Information-ExtIEs } }		OPTIONAL,
	...
}

HSDSCH-TDD-Update-Information-ExtIEs NBAP-PROTOCOL-EXTENSION ::= {
	...
}
HSPDSCH-Code-Index ::= INTEGER (1..maxHS-PDSCHCodeNrComp-1)
-- index of first HS-PDSCH code

HSPDSCH-First-Code-Index ::= INTEGER (1..maxHS-PDSCHCodeNrComp-1)
	-- index of first HS-PDSCH code

HSPDSCH-Second-Code-Index ::= INTEGER (1..maxHS-PDSCHCodeNrComp-1)
	-- index of second HS-PDSCH code

HSPDSCH-Second-Code-Support ::= BOOLEAN
	-- true: applied, false: not applied

HSDPA-Associated-PICH-InformationLCR ::= CHOICE {
	hsdpa-PICH-Shared-with-PCH						HSDPA-PICH-Shared-with-PCH,
	hsdpa-PICH-notShared-with-PCHLCR				HSDPA-PICH-notShared-with-PCHLCR,
	...
}


HSDPA-PICH-notShared-with-PCHLCR ::= SEQUENCE {
	hSDPA-PICH-notShared-ID					CommonPhysicalChannelID,
	tdd-ChannelisationCodeLCR				TDD-ChannelisationCodeLCR,
	timeSlotLCR  							TimeSlotLCR,
	midambleShiftLCR						MidambleShiftLCR,
	tdd-PhysicalChannelOffset				TDD-PhysicalChannelOffset,
	repetitionPeriod						RepetitionPeriod,
	repetitionLength						RepetitionLength,
	pagingIndicatorLength					PagingIndicatorLength,
	pICH-Power								PICH-Power,
	second-TDD-ChannelisationCodeLCR		TDD-ChannelisationCodeLCR,
	sttd-Indicator							STTD-Indicator,
	iE-Extensions							ProtocolExtensionContainer { { HSDPA-PICH-notShared-with-PCHLCR-ExtIEs } }		OPTIONAL,
	...
}

HSDPA-PICH-notShared-with-PCHLCR-ExtIEs NBAP-PROTOCOL-EXTENSION ::= {
	...
}


HSDSCH-Common-System-InformationLCR ::= SEQUENCE {
	hsdsch-Common-InformationLCR					HSDSCH-Common-InformationLCR							OPTIONAL,
	commonMACFlow-Specific-InformationLCR			CommonMACFlow-Specific-InfoListLCR						OPTIONAL,
	common-H-RNTI-InformationLCR					Common-H-RNTI-InformationLCR							OPTIONAL,
	sync-InformationLCR								Sync-InformationLCR										OPTIONAL,
	tDD-AckNack-Power-Offset						TDD-AckNack-Power-Offset								OPTIONAL,
	hSSICH-SIRTarget								UL-SIR													OPTIONAL,
	hSSICH-TPC-StepSize								TDD-TPC-UplinkStepSize-LCR								OPTIONAL,
	iE-Extensions									ProtocolExtensionContainer { { HSDSCH-Common-System-InformationLCR-ExtIEs } }		OPTIONAL,
	...
}

HSDSCH-Common-System-InformationLCR-ExtIEs NBAP-PROTOCOL-EXTENSION ::= {
	...
}

HSDSCH-Common-System-Information-ResponseLCR  ::= SEQUENCE {
	hsSCCH-Specific-Information-ResponseLCR			HSSCCH-Specific-InformationRespListLCR				OPTIONAL,
	hARQ-MemoryPartitioning							HARQ-MemoryPartitioning								OPTIONAL,
-- This HARQ Memory Partitioning Information is for the first Frequency repetition, HARQ Memory Partitioning Information for Frequency repetitions 2 and on, should be defined in MultipleFreq-HARQ-MemoryPartitioning-InformationList.
	commonMACFlow-Specific-Info-ResponseLCR			CommonMACFlow-Specific-InfoList-ResponseLCR			OPTIONAL,
	iE-Extensions									ProtocolExtensionContainer { { HSDSCH-Common-System-Information-ResponseLCR-ExtIEs } }		OPTIONAL,
	...
}

HSDSCH-Common-System-Information-ResponseLCR-ExtIEs NBAP-PROTOCOL-EXTENSION ::= {
{ ID id-UARFCNforNt										CRITICALITY ignore	EXTENSION UARFCN	PRESENCE optional}|
-- Applicable to 1.28Mcps TDD when using multiple frequencies. This is the UARFCN for the first Frequency repetition
{ ID id-MultipleFreq-HARQ-MemoryPartitioning-InformationList	CRITICALITY ignore	EXTENSION MultipleFreq-HARQ-MemoryPartitioning-InformationList	PRESENCE optional },
-- Applicable to 1.28Mcps TDD when using multiple frequencies.This HARQ MemoryPartitioning Information is for the 2nd and beyond frequencies.
	...
}

HSDSCH-Common-InformationLCR ::= SEQUENCE {
	cCCH-PriorityQueue-Id											PriorityQueue-Id,
	sRB1-PriorityQueue-Id											PriorityQueue-Id,
	associatedCommon-MACFlowLCR										Common-MACFlow-ID-LCR,
	fACH-Measurement-Occasion-Cycle-Length-Coefficient				FACH-Measurement-Occasion-Cycle-Length-Coefficient				OPTIONAL,
	bCCH-Specific-HSDSCH-RNTI-InformationLCR						BCCH-Specific-HSDSCH-RNTI-InformationLCR					OPTIONAL,
	iE-Extensions						ProtocolExtensionContainer { { HSDSCH-Common-InformationLCR-ExtIEs} }					OPTIONAL,
	...
}

HSDSCH-Common-InformationLCR-ExtIEs NBAP-PROTOCOL-EXTENSION ::= {
	...
}

HSDSCH-Paging-System-InformationLCR ::= SEQUENCE {
	paging-MACFlow-Specific-InformationLCR			Paging-MACFlow-Specific-InformationLCR,
	hSSCCH-Power									DL-Power																OPTIONAL,
	hSPDSCH-Power									DL-Power																OPTIONAL,
	reception-Window-Size							INTEGER(1..16)															OPTIONAL,
	n-PCH											INTEGER(1..8)															OPTIONAL,
	paging-Subchannel-Size							INTEGER(1..3)															OPTIONAL,
	transport-Block-Size-List						Transport-Block-Size-List												OPTIONAL,
	iE-Extensions									ProtocolExtensionContainer { { HSDSCH-Paging-System-InformationLCR-ExtIEs } }		OPTIONAL,
	...
}

HSDSCH-Paging-System-InformationLCR-ExtIEs NBAP-PROTOCOL-EXTENSION ::= {
	...
}

HSDSCH-Paging-System-Information-ResponseLCR ::= SEQUENCE (SIZE (1..maxNrOfPagingMACFlow)) OF HSDSCH-Paging-System-Information-ResponseListLCR

HSDSCH-Paging-System-Information-ResponseListLCR  ::= SEQUENCE {
	pagingMACFlow-ID								Paging-MACFlow-ID,
	bindingID										BindingID									OPTIONAL,
	transportLayerAddress							TransportLayerAddress						OPTIONAL,
	dL-HS-PDSCH-Timeslot-Information-LCR-PSCH-ReconfRqst		DL-HS-PDSCH-Timeslot-Information-LCR-PSCH-ReconfRqst,
	iE-Extensions									ProtocolExtensionContainer { { HSDSCH-Paging-System-Information-ResponseListLCR-ExtIEs } }		OPTIONAL,
	...
}

HSDSCH-Paging-System-Information-ResponseListLCR-ExtIEs NBAP-PROTOCOL-EXTENSION ::= {
	...
}

HS-SCCH-ID-LCR ::= INTEGER (0..255)

HSSCCH-Specific-InformationRespListLCR ::= SEQUENCE (SIZE (1..maxNrOfHSSCCHsLCR)) OF HSSCCH-Specific-InformationRespItemLCR

HSSCCH-Specific-InformationRespItemLCR ::= SEQUENCE {
	hS-SCCH-ID-LCR									HS-SCCH-ID-LCR,
	iE-Extensions									ProtocolExtensionContainer { { HSSCCH-Specific-InformationRespItemLCR-ExtIEs } }		OPTIONAL,
	...
}

HSSCCH-Specific-InformationRespItemLCR-ExtIEs NBAP-PROTOCOL-EXTENSION ::= {
	...
}
HS-DSCH-Semi-PersistentScheduling-Information-LCR ::= SEQUENCE {
	transport-Block-Size-List				Transport-Block-Size-List-LCR,
	repetition-Period-List-LCR				Repetition-Period-List-LCR,
	hS-DSCH-SPS-Reservation-Indicator		SPS-Reservation-Indicator				OPTIONAL,
	hS-DSCH-SPS-Operation-Indicator			HS-DSCH-SPS-Operation-Indicator,
	iE-Extensions							ProtocolExtensionContainer { { HS-DSCH-Semi-PersistentScheduling-Information-LCR-ExtIEs } }			OPTIONAL,
	...
}

HS-DSCH-Semi-PersistentScheduling-Information-LCR-ExtIEs NBAP-PROTOCOL-EXTENSION ::= {
	...
}

Transport-Block-Size-List-LCR ::= SEQUENCE (SIZE (1..maxNoOfTBSs-Mapping-HS-DSCH-SPS)) OF Transport-Block-Size-Item-LCR

Transport-Block-Size-Item-LCR ::= SEQUENCE {
	transport-Block-Size-maping-Index-LCR		Transport-Block-Size-maping-Index-LCR,
	transport-Block-Size-Index-LCR				Transport-Block-Size-Index-LCR,
	iE-Extensions								ProtocolExtensionContainer { { Transport-Block-Size-Item-LCR-ExtIEs } }			OPTIONAL,
	...
}

Transport-Block-Size-Item-LCR-ExtIEs NBAP-PROTOCOL-EXTENSION ::= {
	...
}

Transport-Block-Size-maping-Index-LCR ::= INTEGER (0..maxNoOfTBSs-Mapping-HS-DSCH-SPS-1)

Transport-Block-Size-Index-LCR ::= INTEGER (1..maxNoOfHS-DSCH-TBSsLCR)

Repetition-Period-List-LCR ::= SEQUENCE (SIZE (1..maxNoOfRepetition-Period-LCR)) OF Repetition-Period-Item-LCR

Repetition-Period-Item-LCR ::= SEQUENCE {
	repetitionPeriodIndex		RepetitionPeriodIndex,
	repetitionPeriod			RepetitionPeriod,
	repetitionLength			RepetitionLength				OPTIONAL,
	iE-Extensions				ProtocolExtensionContainer { { Repetition-Period-Item-LCR-ExtIEs } }			OPTIONAL,
	...
}

Repetition-Period-Item-LCR-ExtIEs NBAP-PROTOCOL-EXTENSION ::= {
	...
}

RepetitionPeriodIndex ::= INTEGER (0..maxNoOfRepetitionPeriod-SPS-LCR-1)

SPS-Reservation-Indicator ::= ENUMERATED {
	reserve
}

HS-DSCH-SPS-Operation-Indicator ::= CHOICE {
	logicalChannellevel			LogicalChannellevel,
	priorityQueuelevel			PriorityQueuelevel,
	...
}

LogicalChannellevel ::= BIT STRING (SIZE (16))

PriorityQueuelevel ::= BIT STRING (SIZE (8))

HS-DSCH-Semi-PersistentScheduling-Information-to-Modify-LCR ::= SEQUENCE {
	transport-Block-Size-List				Transport-Block-Size-List-LCR			OPTIONAL,
	repetition-Period-List-LCR				Repetition-Period-List-LCR				OPTIONAL,
	iE-Extensions							ProtocolExtensionContainer { { HS-DSCH-Semi-PersistentScheduling-Information-to-Modify-LCR-ExtIEs } }							OPTIONAL,
	...
}

HS-DSCH-Semi-PersistentScheduling-Information-to-Modify-LCR-ExtIEs NBAP-PROTOCOL-EXTENSION ::= {
{ ID id-HS-DSCH-SPS-Reservation-Indicator		CRITICALITY ignore	EXTENSION SPS-Reservation-Indicator	PRESENCE optional }|
{ ID id-HS-DSCH-SPS-Operation-Indicator			CRITICALITY reject	EXTENSION HS-DSCH-SPS-Operation-Indicator	PRESENCE optional },
	...
}

HS-DSCH-Semi-PersistentScheduling-Information-ResponseLCR ::= SEQUENCE {
	hS-SICH-InformationList-for-HS-DSCH-SPS		HS-SICH-InformationList-for-HS-DSCH-SPS,
	initial-HS-PDSCH-SPS-Resource				Initial-HS-PDSCH-SPS-Resource			OPTIONAL,
	buffer-Size-for-HS-DSCH-SPS					Process-Memory-Size						OPTIONAL,
	number-of-Processes-for-HS-DSCH-SPS			Number-of-Processes-for-HS-DSCH-SPS		OPTIONAL,
	iE-Extensions								ProtocolExtensionContainer { { HS-DSCH-Semi-PersistentScheduling-Information-ResponseLCR-ExtIEs } }			OPTIONAL,
	...
}

HS-DSCH-Semi-PersistentScheduling-Information-ResponseLCR-ExtIEs NBAP-PROTOCOL-EXTENSION ::= {
	...
}

HS-SICH-InformationList-for-HS-DSCH-SPS ::= SEQUENCE (SIZE (1..maxNoOf-HS-SICH-SPS)) OF HS-SICH-InformationItem-for-HS-DSCH-SPS

HS-SICH-InformationItem-for-HS-DSCH-SPS ::= SEQUENCE {
	hS-SICH-Mapping-Index			HS-SICH-Mapping-Index			OPTIONAL,
	-- the IE is madatory for 1.28Mcps TDD.
	hS-SICH-Type					HS-SICH-Type,
	iE-Extensions					ProtocolExtensionContainer { { HS-SICH-InformationItem-for-HS-DSCH-SPS-ExtIEs } }			OPTIONAL,
	...
}

HS-SICH-InformationItem-for-HS-DSCH-SPS-ExtIEs NBAP-PROTOCOL-EXTENSION ::= {
	...
}

HS-SICH-Mapping-Index ::= INTEGER (0..maxNoOf-HS-SICH-SPS-1)

HS-SICH-Type ::= CHOICE {
	hS-SCCH-Associated-HS-SICH			HS-SCCH-Associated-HS-SICH,
	non-HS-SCCH-Associated-HS-SICH		Non-HS-SCCH-Associated-HS-SICH,
	...
}


HS-SCCH-Associated-HS-SICH ::= SEQUENCE {
	hsSICH-ID							HS-SICH-ID,
	extended-HS-SICH-ID					Extended-HS-SICH-ID			OPTIONAL,
...
}


Non-HS-SCCH-Associated-HS-SICH::= SEQUENCE {
	non-HS-SCCH-Aassociated-HS-SICH-ID	Non-HS-SCCH-Aassociated-HS-SICH-ID,
...
}

Non-HS-SCCH-Aassociated-HS-SICH-ID ::= INTEGER (0..255)

Initial-HS-PDSCH-SPS-Resource::= SEQUENCE {
	repetitionPeriodIndex						RepetitionPeriodIndex,
	repetitionLength							RepetitionLength			OPTIONAL,
	-- the IE is not used.
	hS-PDSCH-Offset								TDD-PhysicalChannelOffset,
	timeslot-Resource-Related-Information		HS-DSCH-TimeslotResourceLCR,
	startCode									TDD-ChannelisationCode,
	endCode										TDD-ChannelisationCode,
	transport-Block-Size-Index					Transport-Block-Size-Index-LCR,
	modulationType								ModulationSPS-LCR,
	hS-SICH-Mapping-Index						HS-SICH-Mapping-Index,
	iE-Extensions								ProtocolExtensionContainer { { Initial-HS-PDSCH-SPS-Resource-ExtIEs } }			OPTIONAL,
...
}

Initial-HS-PDSCH-SPS-Resource-ExtIEs NBAP-PROTOCOL-EXTENSION ::= {
	{ ID id-MidambleShiftLCR	CRITICALITY reject	EXTENSION MidambleShiftLCR		PRESENCE	optional },
	-- mandaroty for 1.28Mcps TDD.
	...
}

HS-DSCH-TimeslotResourceLCR ::= BIT STRING (SIZE (5))

ModulationSPS-LCR ::= ENUMERATED {
	qPSK,
	sixteenQAM,
	...
}

Number-of-Processes-for-HS-DSCH-SPS ::= INTEGER (1..16)

Add-To-Non-HS-SCCH-Associated-HS-SICH-Resource-Pool-LCR-PSCH-ReconfRqst::= SEQUENCE {
	non-HS-SCCH-Associated-HS-SICH-InformationList		Non-HS-SCCH-Associated-HS-SICH-InformationList,
	iE-Extensions										ProtocolExtensionContainer { { Add-To-Non-HS-SCCH-Associated-HS-SICH-Resource-Pool-LCR-PSCH-ReconfRqst-ExtIEs } }			OPTIONAL,
...
}

Add-To-Non-HS-SCCH-Associated-HS-SICH-Resource-Pool-LCR-PSCH-ReconfRqst-ExtIEs NBAP-PROTOCOL-EXTENSION ::= {
	{ ID id-Add-To-Non-HS-SCCH-Associated-HS-SICH-Resource-Pool-LCR-PSCH-ReconfRqst-Ext	CRITICALITY reject	EXTENSION Non-HS-SCCH-Associated-HS-SICH-InformationList-Ext		PRESENCE	optional },
	...
}

Non-HS-SCCH-Associated-HS-SICH-InformationList ::= SEQUENCE (SIZE (0..maxNoOfNon-HS-SCCH-Assosiated-HS-SICH)) OF Non-HS-SCCH-Associated-HS-SICH-InformationItem

Non-HS-SCCH-Associated-HS-SICH-InformationList-Ext ::= SEQUENCE (SIZE (0..maxNoOfNon-HS-SCCH-Assosiated-HS-SICH-Ext)) OF Non-HS-SCCH-Associated-HS-SICH-InformationItem

Non-HS-SCCH-Associated-HS-SICH-InformationItem ::= SEQUENCE {
	non-HS-SCCH-Aassociated-HS-SICH-ID		Non-HS-SCCH-Aassociated-HS-SICH-ID,
	timeSlotLCR								TimeSlotLCR,
	midambleShiftLCR						MidambleShiftLCR,
	tdd-ChannelisationCode					TDD-ChannelisationCode,
	uARFCN									UARFCN						OPTIONAL,
	iE-Extensions							ProtocolExtensionContainer { { Non-HS-SCCH-Associated-HS-SICH-InformationItem-ExtIEs } }			OPTIONAL,
	...
}

Non-HS-SCCH-Associated-HS-SICH-InformationItem-ExtIEs NBAP-PROTOCOL-EXTENSION ::= {
	...
}


Modify-Non-HS-SCCH-Associated-HS-SICH-Resource-Pool-LCR-PSCH-ReconfRqst::= SEQUENCE {
	modify-non-HS-SCCH-Associated-HS-SICH-InformationList		Modify-Non-HS-SCCH-Associated-HS-SICH-InformationList,
	iE-Extensions						ProtocolExtensionContainer { { Modify-Non-HS-SCCH-Associated-HS-SICH-Resource-Pool-LCR-PSCH-ReconfRqst-ExtIEs } }			OPTIONAL,
...
}

Modify-Non-HS-SCCH-Associated-HS-SICH-Resource-Pool-LCR-PSCH-ReconfRqst-ExtIEs NBAP-PROTOCOL-EXTENSION ::= {
	{ ID id-Modify-Non-HS-SCCH-Associated-HS-SICH-Resource-Pool-LCR-PSCH-ReconfRqst-Ext	CRITICALITY reject	EXTENSION Modify-Non-HS-SCCH-Associated-HS-SICH-InformationList-Ext		PRESENCE	optional },
	...
}

Modify-Non-HS-SCCH-Associated-HS-SICH-InformationList ::= SEQUENCE (SIZE (0..maxNoOfNon-HS-SCCH-Assosiated-HS-SICH)) OF Modify-Non-HS-SCCH-Associated-HS-SICH-InformationItem

Modify-Non-HS-SCCH-Associated-HS-SICH-InformationList-Ext ::= SEQUENCE (SIZE (0.. maxNoOfNon-HS-SCCH-Assosiated-HS-SICH-Ext)) OF Modify-Non-HS-SCCH-Associated-HS-SICH-InformationItem

Modify-Non-HS-SCCH-Associated-HS-SICH-InformationItem ::= SEQUENCE {
	non-HS-SCCH-Aassociated-HS-SICH-ID		Non-HS-SCCH-Aassociated-HS-SICH-ID,
	timeSlotLCR								TimeSlotLCR						OPTIONAL,
	midambleShiftLCR						MidambleShiftLCR				OPTIONAL,
	tdd-ChannelisationCode					TDD-ChannelisationCode			OPTIONAL,
	uARFCN									UARFCN							OPTIONAL,
	iE-Extensions							ProtocolExtensionContainer { { Modify-Non-HS-SCCH-Associated-HS-SICH-InformationItem-ExtIEs } }			OPTIONAL,
	...
}

Modify-Non-HS-SCCH-Associated-HS-SICH-InformationItem-ExtIEs NBAP-PROTOCOL-EXTENSION ::= {
	...
}


Delete-From-Non-HS-SCCH-Associated-HS-SICH-Resource-Pool-LCR-PSCH-ReconfRqst ::= SEQUENCE (SIZE (0..maxNoOfNon-HS-SCCH-Assosiated-HS-SICH)) OF Delete-From-Non-HS-SCCH-Associated-HS-SICH-Resource-Pool-LCR-PSCH-ReconfRqstItem

Delete-From-Non-HS-SCCH-Associated-HS-SICH-Resource-Pool-LCR-PSCH-ReconfRqst-Ext ::= SEQUENCE (SIZE (0..maxNoOfNon-HS-SCCH-Assosiated-HS-SICH-Ext)) OF Delete-From-Non-HS-SCCH-Associated-HS-SICH-Resource-Pool-LCR-PSCH-ReconfRqstItem

Delete-From-Non-HS-SCCH-Associated-HS-SICH-Resource-Pool-LCR-PSCH-ReconfRqstItem ::= SEQUENCE {
non-HS-SCCH-Aassociated-HS-SICH-ID			Non-HS-SCCH-Aassociated-HS-SICH-ID,
...
}

MIMO-ReferenceSignal-InformationListLCR ::= SEQUENCE (SIZE (1..maxNrOfHSSCCHCodes)) OF HSSICH-ReferenceSignal-InformationLCR

HSSICH-ReferenceSignal-InformationLCR ::= SEQUENCE {
	midambleConfigurationLCR		MidambleConfigurationLCR,
	midambleShift					INTEGER (0..15),
	timeSlotLCR						TimeSlotLCR,
	iE-Extensions					ProtocolExtensionContainer { { HSSICH-ReferenceSignal-InformationLCR-ExtIEs } }		OPTIONAL,
	...
}

HSSICH-ReferenceSignal-InformationLCR-ExtIEs NBAP-PROTOCOL-EXTENSION ::= {
	...
}

HSSICH-ReferenceSignal-InformationModifyLCR ::= SEQUENCE {
	hSSICH-ReferenceSignal-InformationLCR		HSSICH-ReferenceSignal-InformationLCR	OPTIONAL,
	iE-Extensions					ProtocolExtensionContainer { { HSSICH-ReferenceSignal-InformationModifyLCR-ExtIEs } }		OPTIONAL,
	...
}

HSSICH-ReferenceSignal-InformationModifyLCR-ExtIEs NBAP-PROTOCOL-EXTENSION ::= {
	...
}

-- ==========================================
--	I
-- ==========================================

IB-OC-ID ::= INTEGER (1..16)

IB-SG-DATA ::= BIT STRING
-- Contains SIB data fixed" or "SIB data variable" in segment as encoded in ref.[18].

IB-SG-POS ::= INTEGER (0..4094)
-- Only even positions allowed

IB-SG-REP ::= ENUMERATED {rep4, rep8, rep16, rep32, rep64, rep128, rep256, rep512, rep1024, rep2048, rep4096}

IB-Type ::= ENUMERATED {
	mIB,
	sB1,
	sB2,
	sIB1,
	sIB2,
	sIB3,
	sIB4,
	sIB5,
	sIB6,
	sIB7,
	not-Used-sIB8,
	not-Used-sIB9,
	not-Used-sIB10,
	sIB11,
	sIB12,
	sIB13,
	sIB13dot1,
	sIB13dot2,
	sIB13dot3,
	sIB13dot4,
	sIB14,
	sIB15,
	sIB15dot1,
	sIB15dot2,
	sIB15dot3,
	sIB16,
	...,
	sIB17,
	sIB15dot4,
	sIB18,
	sIB15dot5,
	sIB5bis,
	sIB11bis,
	sIB15bis,
	sIB15dot1bis,
	sIB15dot2bis,
	sIB15dot3bis,
	sIB15dot6,
	sIB15dot7,
	sIB15dot8,
	sIB15dot2ter,
	sIB19
}

IMB-Parameters ::= SEQUENCE {
	sub-Frame-Number						Sub-Frame-Number,
	fdd-dl-ChannelisationCodeNumber			FDD-DL-ChannelisationCodeNumber							OPTIONAL,
	ie-Extensions							ProtocolExtensionContainer { { IMB-Parameters-ExtIEs} }	OPTIONAL,
	...
}

IMB-Parameters-ExtIEs NBAP-PROTOCOL-EXTENSION ::= {
	...
}


Inactivity-Threshold-for-UE-DRX-Cycle ::= ENUMERATED {v0, v1, v2, v4, v8, v16, v32, v64, v128, v256, v512}
-- Unit subframe

Inactivity-Threshold-for-UE-DTX-Cycle2 ::= ENUMERATED {v1, v4, v8, v16, v32, v64, v128, v256}
-- Unit E-DCH TTI

Inactivity-Threshold-for-UE-Grant-Monitoring ::= ENUMERATED {v0, v1, v2, v4, v8, v16, v32, v64, v128, v256}
-- Unit E-DCH TTI


InformationReportCharacteristics ::= CHOICE {
	onDemand				NULL,
	periodic				InformationReportCharacteristicsType-ReportPeriodicity,
	onModification          InformationReportCharacteristicsType-OnModification,
	...
}

InformationReportCharacteristicsType-ReportPeriodicity ::= CHOICE {
	min 				ReportPeriodicity-Scaledmin,
	hours				ReportPeriodicity-Scaledhour,
	...
}

InformationReportCharacteristicsType-OnModification ::= SEQUENCE {
    information-thresholds        InformationThresholds		OPTIONAL,
    ie-Extensions		          ProtocolExtensionContainer { { InformationReportCharacteristicsType-OnModification-ExtIEs} }	OPTIONAL,
   ...
}

InformationReportCharacteristicsType-OnModification-ExtIEs NBAP-PROTOCOL-EXTENSION ::= {
	...
}

InformationThresholds ::= CHOICE {
    dgps                DGPSThresholds,
   	...,
	dGANSSThreshold		DGANSSThreshold
}

InformationExchangeID ::= INTEGER (0..1048575)

InformationType ::= SEQUENCE {
	information-Type-Item		Information-Type-Item,
	gPSInformation  			GPS-Information													OPTIONAL,
	-- The IE shall be present if the Information Type Item IE indicates "GPS Information".
	iE-Extensions				ProtocolExtensionContainer { { Information-Type-ExtIEs} }		OPTIONAL,
	...
}

Information-Type-ExtIEs NBAP-PROTOCOL-EXTENSION ::= {
-- The following IE shall be present if the Information Type Item IE indicates 'GANSS Information'
	{ ID id-GANSS-Information			CRITICALITY ignore	EXTENSION GANSS-Information			PRESENCE conditional }|
-- The following IE shall be present if the Information Type Item IE indicates 'DGANSS Corrections'
	{ ID id-DGANSS-Corrections-Req		CRITICALITY ignore	EXTENSION DGANSS-Corrections-Req	PRESENCE conditional },
	...
}

Information-Type-Item ::= ENUMERATED {
    gpsinformation,
    dgpscorrections,
    gpsrxpos,
    ...,
	gANSSInformation,
	dGANSSCorrections,
	gANSS-RX-Pos
}

Initial-DL-DPCH-TimingAdjustment-Allowed ::= ENUMERATED {
	initial-DL-DPCH-TimingAdjustment-Allowed
}

InnerLoopDLPCStatus ::= ENUMERATED {
	active,
	inactive
}

IPDL-Indicator ::= ENUMERATED {
	active,
	inactive
}


IPDL-FDD-Parameters ::= SEQUENCE {
	iP-SpacingFDD					ENUMERATED{sp5,sp7,sp10,sp15,sp20,sp30,sp40,sp50,...},
	iP-Length						ENUMERATED{len5, len10},
	seed							INTEGER(0..63),
	burstModeParams					BurstModeParams		OPTIONAL,
	iP-Offset						INTEGER(0..9),
	iE-Extensions					ProtocolExtensionContainer { { IPDLFDDParameter-ExtIEs} }	OPTIONAL,
	...
}

IPDLFDDParameter-ExtIEs NBAP-PROTOCOL-EXTENSION ::= {
	...
}

IPDL-TDD-Parameters ::= SEQUENCE {
	iP-SpacingTDD					ENUMERATED{sp30,sp40,sp50,sp70,sp100,...},
	iP-Start						INTEGER(0..4095),
	iP-Slot							INTEGER(0..14),
	iP-PCCPCH						ENUMERATED{switchOff-1-Frame,switchOff-2-Frames},
	burstModeParams					BurstModeParams		OPTIONAL,
	iE-Extensions			ProtocolExtensionContainer { { IPDLTDDParameter-ExtIEs} }	OPTIONAL,
	...
}

IPDL-TDD-Parameters-LCR ::= SEQUENCE {
	iP-SpacingTDD					ENUMERATED{sp30,sp40,sp50,sp70,sp100,...},
	iP-Start						INTEGER(0..4095),
	iP-Sub							ENUMERATED{first,second,both},
	burstModeParams					BurstModeParams		OPTIONAL,
	iE-Extensions			ProtocolExtensionContainer { { IPDLTDDParameterLCR-ExtIEs} }	OPTIONAL,
	...
}

IPMulticastIndication ::= SEQUENCE {
	transportLayerAddress			TransportLayerAddress,
	bindingID						BindingID,
	cFNOffset						INTEGER(0..255),
	iE-Extensions			ProtocolExtensionContainer { { IPMulticastIndication-ExtIEs} }	OPTIONAL,
	...
}

IPMulticastIndication-ExtIEs NBAP-PROTOCOL-EXTENSION ::= {
	...
}

IPMulticastDataBearerIndication ::= BOOLEAN
-- true: IP Multicast used, false: IP Multicast not used

BurstModeParams ::= SEQUENCE {
	burstStart							INTEGER(0..15),
	burstLength							INTEGER(10..25),
	burstFreq							INTEGER(1..16),
	...
}

IPDLTDDParameter-ExtIEs NBAP-PROTOCOL-EXTENSION ::= {
	...
}

IPDLTDDParameterLCR-ExtIEs NBAP-PROTOCOL-EXTENSION ::= {
	...
}

IdleIntervalInformation	::= SEQUENCE {
	idleIntervalInfo-k							INTEGER{none(0),two(2),three(3)} (0..3),
	idleIntervalInfo-offset						INTEGER(0..7),
	...
}


-- ==========================================
--	J
-- ==========================================

-- ==========================================
--	K
-- ==========================================

-- ==========================================
--	L
-- ==========================================

LimitedPowerIncrease ::= ENUMERATED {
	used,
	not-used
}

Local-Cell-ID ::= INTEGER (0..268435455)

LTGI-Presence ::= BOOLEAN
-- True = the Long Term Grant Indicator shall be used within E-DCH grants

LCRTDD-Uplink-Physical-Channel-Capability ::= SEQUENCE {
	maxTimeslotsPerSubFrame				INTEGER(1..6),
	maxPhysChPerTimeslot				ENUMERATED {one,two,...,three,four},
	iE-Extensions						ProtocolExtensionContainer { { LCRTDD-Uplink-Physical-Channel-Capability-ExtIEs} } OPTIONAL,
	...
}

LCRTDD-Uplink-Physical-Channel-Capability-ExtIEs NBAP-PROTOCOL-EXTENSION ::= {
	...
}

-- ==========================================
--	M
-- ==========================================

MAC-DTX-Cycle-2ms ::= ENUMERATED {v1, v4, v5, v8, v10, v16, v20}

MAC-DTX-Cycle-10ms ::= ENUMERATED {v5, v10, v20}

MAC-ehs-Reset-Timer ::= ENUMERATED {v1, v2, v3, v4,...}

MACdPDU-Size ::= INTEGER (1..5000,...)
	-- In case of E-DCH value 8 and values not multiple of 8 shall not be used

MAC-PDU-SizeExtended ::= INTEGER (1..1504,...,1505)
	-- In case of E-DCH value 1 shall not be used

MAC-Inactivity-Threshold ::= ENUMERATED {v1, v2, v4, v8, v16, v32, v64, v128, v256, v512, infinity}
	-- Unit subframe

MACdPDU-Size-Indexlist ::= SEQUENCE (SIZE (1..maxNrOfMACdPDUIndexes)) OF MACdPDU-Size-IndexItem

MACdPDU-Size-IndexItem ::= SEQUENCE {
	sID									SID,
	macdPDU-Size						MACdPDU-Size,
	iE-Extensions						ProtocolExtensionContainer { { MACdPDU-Size-IndexItem-ExtIEs} }		OPTIONAL,
	...
}

MACdPDU-Size-IndexItem-ExtIEs NBAP-PROTOCOL-EXTENSION ::= {
	...
}

MACdPDU-Size-Indexlist-to-Modify ::= SEQUENCE (SIZE (1..maxNrOfMACdPDUIndexes)) OF MACdPDU-Size-IndexItem-to-Modify

MACdPDU-Size-IndexItem-to-Modify ::= SEQUENCE {
	sID									SID,
	macdPDU-Size						MACdPDU-Size,
	iE-Extensions						ProtocolExtensionContainer { { MACdPDU-Size-IndexItem-to-Modify-ExtIEs} }		OPTIONAL,
	...
}

MACdPDU-Size-IndexItem-to-Modify-ExtIEs NBAP-PROTOCOL-EXTENSION ::= {
	...
}

MACesGuaranteedBitRate ::= INTEGER (0..16777215,...,16777216..256000000)

MACes-Maximum-Bitrate-LCR ::= INTEGER (0..256000000,...)

MACeReset-Indicator ::= ENUMERATED {mACeReset}

MAChsGuaranteedBitRate ::= INTEGER (0..16777215,...,16777216..256000000)

MAChsReorderingBufferSize-for-RLC-UM ::= INTEGER (0..300,...)
-- Unit kBytes

MAC-hsWindowSize		::= ENUMERATED {v4, v6, v8, v12, v16, v24, v32,..., v64, v128}
-- For 1.28Mcps TDD when TSN length is configured to 9bits, ENUMERATED (32, 64, 96, 128, 160, 192, 256,...)


MAChsResetScheme ::= ENUMERATED {
	always,
	interNodeB-change
}


MaximumDL-PowerCapability ::=  INTEGER(0..500)
-- Unit dBm, Range 0dBm .. 50dBm, Step +0.1dB

Max-Bits-MACe-PDU-non-scheduled ::= INTEGER(1..maxNrOfBits-MACe-PDU-non-scheduled)

Max-EDCH-Resource-Allocation-for-CCCH ::= ENUMERATED {v8, v12, v16, v24, v32, v40, v80, v120,...}

Max-Period-for-Collistion-Resolution ::= INTEGER(8..24,...)

Max-TB-Sizes ::= SEQUENCE {
	maximum-TB-Size-cell-edge-users		INTEGER (0..5000,...),
	maximum-TB-Size-other-users			INTEGER (0..5000,...),
	iE-Extensions						ProtocolExtensionContainer { {Max-TB-Sizes-ExtIEs} } OPTIONAL,
	...
	}


Max-TB-Sizes-ExtIEs  NBAP-PROTOCOL-EXTENSION ::= {
	...
}

Maximum-Number-of-Retransmissions-For-E-DCH ::= INTEGER (0..15)

Maximum-Target-ReceivedTotalWideBandPower-LCR ::= INTEGER (0..621)
-- mapping as for RTWP measurement value, as specified in [23]

MaximumTransmissionPower ::=  INTEGER(0..500)
-- Unit dBm, Range 0dBm .. 50dBm, Step +0.1dB


MaxNrOfUL-DPDCHs ::= INTEGER (1..6)

MaxPRACH-MidambleShifts ::= ENUMERATED {
	shift4,
	shift8,
	...,
	shift16
}

Max-Set-E-DPDCHs ::= ENUMERATED {
	vN256, vN128, vN64, vN32, vN16, vN8, vN4, v2xN4, v2xN2, v2xN2plus2xN4,
	...,
	v2xM2plus2xM4
	}
-- Values related to [8]

Max-UE-DTX-Cycle ::= ENUMERATED {
	v5, v10, v20, v40, v64, v80, v128, v160,
	...
	}


MBMS-Capability ::= ENUMERATED{
mbms-capable,
mbms-non-capable
}


MeasurementFilterCoefficient ::= ENUMERATED {k0, k1, k2, k3, k4, k5, k6, k7, k8, k9, k11, k13, k15, k17, k19,...}
-- Measurement Filter Coefficient to be used for measurement

MeasurementID ::= INTEGER (0..1048575)

Measurement-Power-Offset ::= INTEGER(-12 .. 26)
-- Actual value = IE value * 0.5

MeasurementRecoveryBehavior ::= NULL

MeasurementRecoveryReportingIndicator ::= NULL

MeasurementRecoverySupportIndicator ::= NULL

MessageStructure ::= SEQUENCE (SIZE (1..maxNrOfLevels)) OF
	SEQUENCE {
		iE-ID					ProtocolIE-ID,
		repetitionNumber		RepetitionNumber1		OPTIONAL,
		iE-Extensions			ProtocolExtensionContainer { {MessageStructure-ExtIEs} } OPTIONAL,
		...
	}

MessageStructure-ExtIEs NBAP-PROTOCOL-EXTENSION ::= {
	...
}

MICH-CFN ::= INTEGER (0..4095)

MICH-Mode ::= ENUMERATED {
	v18,
	v36,
	v72,
	v144,
	...,
	v16,
	v32,
	v64,
	v128
}

MidambleConfigurationLCR ::=	ENUMERATED {v2, v4, v6, v8, v10, v12, v14, v16, ...}

MidambleConfigurationBurstType1And3 ::=		ENUMERATED {v4, v8, v16}

MidambleConfigurationBurstType2 ::=		ENUMERATED {v3, v6}

MidambleShiftAndBurstType ::=		CHOICE {
	type1								SEQUENCE {
		midambleConfigurationBurstType1And3	MidambleConfigurationBurstType1And3,
		midambleAllocationMode 				CHOICE {
			defaultMidamble						NULL,
			commonMidamble						NULL,
			ueSpecificMidamble					MidambleShiftLong,
			...
		},
	...
	},
	type2								SEQUENCE {
		midambleConfigurationBurstType2		MidambleConfigurationBurstType2,
		midambleAllocationMode 				CHOICE {
			defaultMidamble						NULL,
			commonMidamble						NULL,
			ueSpecificMidamble					MidambleShiftShort,
			...
		},
		...
	},
	type3								SEQUENCE {
		midambleConfigurationBurstType1And3	MidambleConfigurationBurstType1And3,
		midambleAllocationMode 				CHOICE {
			defaultMidamble						NULL,
			ueSpecificMidamble					MidambleShiftLong,
		...
		},
		...
	},
	...
}

MidambleShiftLong ::=				INTEGER (0..15)

MidambleShiftShort ::=				INTEGER (0..5)

MidambleShiftLCR ::= SEQUENCE {
	midambleAllocationMode		MidambleAllocationMode,
	midambleShift				MidambleShiftLong		OPTIONAL,
	-- The IE shall be present if the Midamble Allocation Mode IE is set to "UE specific midamble".
midambleConfigurationLCR		MidambleConfigurationLCR,
	iE-Extensions				ProtocolExtensionContainer { {MidambleShiftLCR-ExtIEs} }		OPTIONAL,
	...
	}

MidambleAllocationMode ::= ENUMERATED {
	defaultMidamble,
	commonMidamble,
	uESpecificMidamble,
	...
	}

MidambleShiftLCR-ExtIEs  NBAP-PROTOCOL-EXTENSION ::= {
	...
}

MidambleShiftAndBurstType768 ::=		CHOICE {
	type1								SEQUENCE {
		midambleConfigurationBurstType1And3		MidambleConfigurationBurstType1And3,
		midambleAllocationMode 				CHOICE {
			defaultMidamble						NULL,
			commonMidamble						NULL,
			ueSpecificMidamble					MidambleShiftLong,
			...
		},
		...
	},
	type2								SEQUENCE {
		midambleConfigurationBurstType2-768		MidambleConfigurationBurstType2-768,
		midambleAllocationMode 				CHOICE {
			defaultMidamble						NULL,
			commonMidamble						NULL,
			ueSpecificMidamble					MidambleShiftShort768,
			...
		},
		...
	},
	type3								SEQUENCE {
		midambleConfigurationBurstType1And3	MidambleConfigurationBurstType1And3,
		midambleAllocationMode 			CHOICE {
			defaultMidamble						NULL,
			ueSpecificMidamble					MidambleShiftLong,
			...
		},
		...
	},
	...
}

MidambleConfigurationBurstType2-768 ::=		ENUMERATED {v4, v8}

MidambleShiftShort768 ::=				INTEGER (0..7)

MIMO-ActivationIndicator ::= NULL

MIMO-Capability ::= ENUMERATED {
	mimo-capable,
	mimo-non-capable
}


MIMO-Mode-Indicator ::= ENUMERATED {
	activate,
	deactivate
}

MIMO-N-M-Ratio ::= ENUMERATED {v1-2, v2-3, v3-4, v4-5, v5-6, v6-7, v7-8, v8-9, v9-10, v1-1,...}

MIMO-PilotConfiguration ::= CHOICE {
	primary-and-secondary-CPICH				CommonPhysicalChannelID,
	normal-and-diversity-primary-CPICH		NULL,
	...
}

MIMO-PilotConfigurationExtension ::= CHOICE {
	primary-and-secondary-CPICH				PrimaryAndSecondaryCPICHContainer,
	normal-and-diversity-primary-CPICH		NormalAndDiversityPrimaryCPICHContainer,
	...
}


MIMO-PowerOffsetForS-CPICHCapability ::= ENUMERATED {
	s-CPICH-Power-Offset-Capable,
	s-CPICH-Power-Offset-Not-Capable
}

MinimumDL-PowerCapability ::=  INTEGER(0..800)
-- Unit dBm, Range -30dBm .. 50dBm, Step +0.1dB

MinimumReducedE-DPDCH-GainFactor ::= ENUMERATED {m8-15, m11-15, m15-15, m21-15, m30-15, m42-15, m60-15, m84-15,...}

MinSpreadingFactor ::= ENUMERATED {
		v4,
		v8,
		v16,
		v32,
		v64,
		v128,
		v256,
		v512
}
--  TDD Mapping scheme for the minimum spreading factor 1 and 2: "256" means 1, "512" means 2

Modification-Period ::= ENUMERATED { v1280, v2560, v5120, v10240,...}

ModifyPriorityQueue ::= CHOICE {
	addPriorityQueue			PriorityQueue-InfoItem-to-Add,
	modifyPriorityQueue			PriorityQueue-InfoItem-to-Modify,
	deletePriorityQueue			PriorityQueue-Id,
	...
}

Modulation ::= ENUMERATED {
	qPSK,
	eightPSK,
	-- 8PSK denotes 16QAM for S-CCPCH
	...
}

MinUL-ChannelisationCodeLength ::= ENUMERATED {
	v4,
	v8,
	v16,
	v32,
	v64,
	v128,
	v256,
	...
}

MultiplexingPosition ::= ENUMERATED {
	fixed,
	flexible
}

MAChs-ResetIndicator ::= ENUMERATED{
	mAChs-NotReset
}

ModulationMBSFN ::= ENUMERATED {
	qPSK,
	sixteenQAM,
	...
}

MBSFN-CPICH-secondary-CCPCH-power-offset ::= INTEGER(-11..4,...)
-- Unit dB, Step 1 dB, Range -11..4 dB.

ModulationPO-MBSFN ::= CHOICE {
	qPSK				NULL,
	sixteenQAM			MBSFN-CPICH-secondary-CCPCH-power-offset,
	...
}
MBSFN-Only-Mode-Indicator ::= ENUMERATED {
	mBSFN-Only-Mode
}

MBSFN-Only-Mode-Capability ::= ENUMERATED {
	mBSFN-Only-Mode-capable,
	mBSFN-Only-Mode-non-capable
}

Multicarrier-Number ::= INTEGER (1..maxHSDPAFrequency)

MultipleFreq-HARQ-MemoryPartitioning-InformationList ::= SEQUENCE (SIZE (1..maxFrequencyinCell-1)) OF MultipleFreq-HARQ-MemoryPartitioning-InformationItem
--Includes the 2nd through the max number of frequencies information repetitions.

MultipleFreq-HARQ-MemoryPartitioning-InformationItem ::= SEQUENCE {
	hARQ-MemoryPartitioning						HARQ-MemoryPartitioning,
	uARFCN										UARFCN,
	iE-Extensions					ProtocolExtensionContainer { { MultipleFreq-HARQ-MemoryPartitioning-InformationItem-ExtIEs} }					OPTIONAL,
	...
}

MultipleFreq-HARQ-MemoryPartitioning-InformationItem-ExtIEs NBAP-PROTOCOL-EXTENSION ::= {
	...
}

MultipleFreq-HSPDSCH-InformationList-ResponseTDDLCR ::= SEQUENCE (SIZE (1.. maxHSDPAFrequency-1)) OF MultipleFreq-HSPDSCH-InformationItem-ResponseTDDLCR
--Includes the 2nd through the max number of frequency repetitions.

MultipleFreq-HSPDSCH-InformationItem-ResponseTDDLCR ::= SEQUENCE{
	hsSCCH-Specific-Information-ResponseTDDLCR		HSSCCH-Specific-InformationRespListTDDLCR	OPTIONAL,
	hARQ-MemoryPartitioning							HARQ-MemoryPartitioning						OPTIONAL,
	uARFCN											UARFCN, -- This is the UARFCN for the second and beyond Frequency repetition.
	iE-Extensions									ProtocolExtensionContainer { { MultipleFreq-HSPDSCH-InformationItem-ResponseTDDLCR-ExtIEs } }		OPTIONAL,
	...
}

MultipleFreq-HSPDSCH-InformationItem-ResponseTDDLCR-ExtIEs NBAP-PROTOCOL-EXTENSION ::= {
...
}

Multi-Cell-Capability ::= ENUMERATED {
	multi-Cell-Capable,
	multi-Cell-non-Capable
}

Multi-Cell-Capability-Info::= SEQUENCE {
	multi-Cell-Capability										Multi-Cell-Capability,
	possible-Secondary-Serving-Cell-List						Possible-Secondary-Serving-Cell-List		OPTIONAL,
	iE-Extensions				ProtocolExtensionContainer { { Multi-Cell-Capability-Info-ExtIEs } }		OPTIONAL,
	...
}

Multi-Cell-Capability-Info-ExtIEs NBAP-PROTOCOL-EXTENSION ::= {
	...
}

Multicell-EDCH-Information		::= ProtocolIE-Single-Container { {Multicell-EDCH-InformationItem} }

Multicell-EDCH-InformationItem NBAP-PROTOCOL-IES ::= {
	{ ID id-Multicell-EDCH-InformationItemIEs	CRITICALITY ignore	TYPE Multicell-EDCH-InformationItemIEs		PRESENCE mandatory }
}

Multicell-EDCH-InformationItemIEs	::= SEQUENCE {
	dL-PowerBalancing-Information				DL-PowerBalancing-Information				OPTIONAL,
	minimumReducedE-DPDCH-GainFactor			MinimumReducedE-DPDCH-GainFactor			OPTIONAL,
	secondary-UL-Frequency-Activation-State		Secondary-UL-Frequency-Activation-State		OPTIONAL,
	iE-Extensions		ProtocolExtensionContainer { { Multicell-EDCH-InformationItemIEs-ExtIEs } } OPTIONAL,
	...

}

Multicell-EDCH-InformationItemIEs-ExtIEs NBAP-PROTOCOL-EXTENSION ::= {
	...
}

Multicell-EDCH-RL-Specific-Information		::= ProtocolIE-Single-Container { { Multicell-EDCH-RL-Specific-InformationItem} }

Multicell-EDCH-RL-Specific-InformationItem NBAP-PROTOCOL-IES ::= {
	{ ID id-Multicell-EDCH-RL-Specific-InformationItemIEs	CRITICALITY ignore	TYPE Multicell-EDCH-RL-Specific-InformationItemIEs		PRESENCE mandatory	}
}

Multicell-EDCH-RL-Specific-InformationItemIEs::= SEQUENCE {
	extendedPropagationDelay					ExtendedPropagationDelay					OPTIONAL,
	primary-CPICH-Usage-for-Channel-Estimation	Primary-CPICH-Usage-for-Channel-Estimation	OPTIONAL,
	secondary-CPICH-Information					CommonPhysicalChannelID						OPTIONAL,
	secondary-CPICH-Information-Change			Secondary-CPICH-Information-Change			OPTIONAL,
	e-AGCH-PowerOffset							E-AGCH-PowerOffset							OPTIONAL,
	e-RGCH-PowerOffset							E-RGCH-PowerOffset							OPTIONAL,
	e-HICH-PowerOffset							E-HICH-PowerOffset							OPTIONAL,
	dLReferencePower							DL-Power									OPTIONAL,
	e-DCH-DL-Control-Channel-Grant				NULL	 									OPTIONAL,
	iE-Extensions		ProtocolExtensionContainer { { Multicell-EDCH-RL-Specific-InformationItemIEs-ExtIEs } } OPTIONAL,
	...

}

Multicell-EDCH-RL-Specific-InformationItemIEs-ExtIEs NBAP-PROTOCOL-EXTENSION ::= {
	...
}

MIMO-SFMode-For-HSPDSCHDualStream ::= ENUMERATED {
	sF1,
	sF1SF16
}

-- ==========================================
--	N
-- ==========================================

Nack-Power-Offset ::= INTEGER (0..8,...)
-- According to mapping in ref. [9] subclause 4.2.1

NCyclesPerSFNperiod ::= ENUMERATED {
	v1,
	v2,
	v4,
	v8,
	...,
	v16,
	v32,
	v64
}

NRepetitionsPerCyclePeriod ::= INTEGER (2..10)

N-INSYNC-IND ::= INTEGER (1..256)

N-OUTSYNC-IND ::= INTEGER (1..256)

N-PROTECT ::= INTEGER(0..7)

NeighbouringCellMeasurementInformation ::= SEQUENCE (SIZE (1..maxNrOfMeasNCell)) OF
		CHOICE {
				neighbouringFDDCellMeasurementInformation		NeighbouringFDDCellMeasurementInformation, -- FDD only
				neighbouringTDDCellMeasurementInformation		NeighbouringTDDCellMeasurementInformation,
				-- Applicable to 3.84Mcps TDD only
				...,
				extension-neighbouringCellMeasurementInformation	Extension-neighbouringCellMeasurementInformation
			}

Extension-neighbouringCellMeasurementInformation	::=	ProtocolIE-Single-Container {{ Extension-neighbouringCellMeasurementInformationIE }}

Extension-neighbouringCellMeasurementInformationIE NBAP-PROTOCOL-IES ::= {
	{ ID id-neighbouringTDDCellMeasurementInformationLCR	CRITICALITY reject	TYPE NeighbouringTDDCellMeasurementInformationLCR	PRESENCE mandatory }|	-- Applicable to 1.28Mcps TDD only
	{ ID id-neighbouringTDDCellMeasurementInformation768	CRITICALITY reject	TYPE NeighbouringTDDCellMeasurementInformation768	PRESENCE mandatory },	-- Applicable to 7.68Mcps TDD only
	...
}

NeighbouringFDDCellMeasurementInformation ::= SEQUENCE {
	uC-Id								UC-Id,
	uARFCN								UARFCN,
	primaryScramblingCode				PrimaryScramblingCode,
	iE-Extensions						ProtocolExtensionContainer { { NeighbouringFDDCellMeasurementInformationItem-ExtIEs} } OPTIONAL,
	...
}

NeighbouringFDDCellMeasurementInformationItem-ExtIEs NBAP-PROTOCOL-EXTENSION ::= {
	...
}

NeighbouringTDDCellMeasurementInformation ::= SEQUENCE {
	uC-Id								UC-Id,
	uARFCN								UARFCN,
	cellParameterID						CellParameterID,
	timeSlot							TimeSlot						OPTIONAL,
	midambleShiftAndBurstType			MidambleShiftAndBurstType		OPTIONAL,
	iE-Extensions						ProtocolExtensionContainer { { NeighbouringTDDCellMeasurementInformationItem-ExtIEs} } OPTIONAL,
	...
}

NeighbouringTDDCellMeasurementInformationItem-ExtIEs NBAP-PROTOCOL-EXTENSION ::= {
	...
}

NeighbouringTDDCellMeasurementInformationLCR ::= SEQUENCE {
	uC-Id								UC-Id,
	uARFCN								UARFCN,
	cellParameterID						CellParameterID,
	timeSlotLCR							TimeSlotLCR				OPTIONAL,
	midambleShiftLCR					MidambleShiftLCR		OPTIONAL,
	iE-Extensions						ProtocolExtensionContainer { { NeighbouringTDDCellMeasurementInformationLCRItem-ExtIEs} } OPTIONAL,
	...
}

NeighbouringTDDCellMeasurementInformationLCRItem-ExtIEs NBAP-PROTOCOL-EXTENSION ::= {
	...
}

NeighbouringTDDCellMeasurementInformation768 ::= SEQUENCE {
	uC-Id								UC-Id,
	uARFCN								UARFCN,
	cellParameterID						CellParameterID,
	timeSlot							TimeSlot						OPTIONAL,
	midambleShiftAndBurstType768		MidambleShiftAndBurstType768		OPTIONAL,
	iE-Extensions						ProtocolExtensionContainer { { NeighbouringTDDCellMeasurementInformation768Item-ExtIEs} } OPTIONAL,
	...
}

NeighbouringTDDCellMeasurementInformation768Item-ExtIEs NBAP-PROTOCOL-EXTENSION ::= {
	...
}

NonCellSpecificTxDiversity ::= ENUMERATED {
	txDiversity,
	...
}

NI-Information ::= SEQUENCE (SIZE (1..maxNrOfNIs)) OF Notification-Indicator

Notification-Indicator ::= INTEGER (0..65535)


NodeB-CommunicationContextID ::= INTEGER (0..1048575)

NormalAndDiversityPrimaryCPICHContainer ::= SEQUENCE {
		iE-Extensions						ProtocolExtensionContainer { { NormalAndDiversityPrimaryCPICHContainer-ExtIEs} } OPTIONAL,
	...
}

NormalAndDiversityPrimaryCPICHContainer-ExtIEs NBAP-PROTOCOL-EXTENSION ::= {
	...
}


NotificationIndicatorLength ::= ENUMERATED {
	v2,
	v4,
	v8,
	...
}


NumberOfReportedCellPortions ::= INTEGER (1..maxNrOfCellPortionsPerCell,...)

NumberOfReportedCellPortionsLCR ::= INTEGER (1..maxNrOfCellPortionsPerCellLCR,...)

Number-of-PCCH-transmission ::= INTEGER (1..5)

NSubCyclesPerCyclePeriod ::= INTEGER (1..16,...)

N-E-UCCH ::= INTEGER (1..12)

N-E-UCCHLCR ::= INTEGER (1..8)

Number-Of-Supported-Carriers  ::= ENUMERATED {
	one-one-carrier,
	one-three-carrier,
	three-three-carrier,
	one-six-carrier,
	three-six-carrier,
	six-six-carrier,
	...
}

NumHS-SCCH-Codes ::= INTEGER (1..maxNrOfHSSCCHCodes)

NoOfTargetCellHS-SCCH-Order::= INTEGER (1..30)

-- ==========================================
--	O
-- ==========================================

Out-of-Sychronization-Window ::= ENUMERATED {
	ms40,
	ms80,
	ms160,
	ms320,
	ms640,
	...
}

-- ==========================================
--	P
-- ==========================================

PagingIndicatorLength ::= ENUMERATED {
	v2,
	v4,
	v8,
	...
}

Paging-MACFlow-ID ::= INTEGER (0..maxNrOfPagingMACFlow-1)


PayloadCRC-PresenceIndicator ::= ENUMERATED {
	cRC-Included,
	cRC-NotIncluded,
	...
}

PCCPCH-Power ::= INTEGER (-150..400,...)
-- PCCPCH-power = power * 10
-- If power <= -15 PCCPCH shall be set to -150
-- If power >= 40 PCCPCH shall be set to 400
-- Unit dBm, Range -15dBm .. +40 dBm, Step +0.1dB

PDSCH-ID ::= INTEGER (0..255)

PDSCH-ID768 ::= INTEGER (0..511)

PDSCHSet-ID ::= INTEGER (0..255)

PICH-Mode ::= ENUMERATED {
	v18,
	v36,
	v72,
	v144,
	...
}

PICH-Power ::= INTEGER (-10..5)
-- Unit dB, Range -10dB .. +5dB, Step +1dB

Paging-MACFlows-to-DeleteFDD ::= SEQUENCE (SIZE (1.. maxNrOfPagingMACFlow)) OF Paging-MACFlows-to-DeleteFDD-Item

Paging-MACFlows-to-DeleteFDD-Item ::= SEQUENCE {
	paging-MACFlow-ID								Paging-MACFlow-ID,
	iE-Extensions									ProtocolExtensionContainer { { Paging-MACFlows-to-DeleteFDD-Item-ExtIEs} }					OPTIONAL,
	...
}

Paging-MACFlows-to-DeleteFDD-Item-ExtIEs NBAP-PROTOCOL-EXTENSION ::= {
	...
}


Paging-MACFlow-Specific-Information ::= SEQUENCE (SIZE (1.. maxNrOfPagingMACFlow)) OF Paging-MAC-Flow-Specific-Information-Item

Paging-MAC-Flow-Specific-Information-Item ::= SEQUENCE {
	paging-MACFlow-Id								Paging-MACFlow-ID,
	hSDPA-associated-PICH-Info						HSDPA-Associated-PICH-Information,
	bindingID										BindingID									OPTIONAL,
	transportLayerAddress							TransportLayerAddress						OPTIONAL,
	tnl-qos											TnlQos										OPTIONAL,
	toAWS											ToAWS,
	toAWE											ToAWE,
	paging-MACFlow-PriorityQueue-Information		Paging-MACFlow-PriorityQueue-Information	OPTIONAL,
	iE-Extensions									ProtocolExtensionContainer { { Paging-MAC-Flow-Specific-Information-Item-ExtIEs } }		OPTIONAL,
	...
}

Paging-MAC-Flow-Specific-Information-Item-ExtIEs NBAP-PROTOCOL-EXTENSION ::= {
	{ ID id-TransportBearerRequestIndicator 	CRITICALITY ignore	 EXTENSION TransportBearerRequestIndicator 	PRESENCE optional},
-- This IE should not be contained if the MAC flow is setup in procedure, and it should be contained if the MAC flow is modified in procedure.
	...
}

Paging-MACFlow-PriorityQueue-Information  ::= SEQUENCE (SIZE (1..maxNrOfpagingMACQueues)) OF Paging-MACFlow-PriorityQueue-Item

Paging-MACFlow-PriorityQueue-Item  ::= SEQUENCE {
	priority-Queue-Information-for-Enhanced-PCH		Priority-Queue-Information-for-Enhanced-FACH-PCH,
		iE-Extensions									ProtocolExtensionContainer { { Paging-MACFlow-PriorityQueue-Item-ExtIEs } }		OPTIONAL,
	...
}

Paging-MACFlow-PriorityQueue-Item-ExtIEs NBAP-PROTOCOL-EXTENSION ::= {
	...
}

Pattern-Sequence-Identifier ::= INTEGER (1.. maxNrOfDCHMeasurementOccasionPatternSequence)

PhysicalChannelID-for-CommonERNTI-RequestedIndicator ::= ENUMERATED {
	requested
}

PLCCHsequenceNumber ::= INTEGER (0..14)

PLCCHinformation ::= SEQUENCE {
	commonPhysicalChannelID					CommonPhysicalChannelID,
	sequenceNumber							PLCCHsequenceNumber,
	iE-Extensions							ProtocolExtensionContainer { { PLCCHinformation-ExtIEs} }		OPTIONAL,
	...
}

PLCCHinformation-ExtIEs  NBAP-PROTOCOL-EXTENSION ::= {
	...
}

Possible-Secondary-Serving-Cell-List ::= SEQUENCE (SIZE (1..maxNrOfHSDSCH-1)) OF Possible-Secondary-Serving-Cell

Possible-Secondary-Serving-Cell ::= SEQUENCE {
	local-Cell-ID				Local-Cell-ID,
	iE-Extensions				ProtocolExtensionContainer { { Possible-Secondary-Serving-Cell-ExtIEs } }			OPTIONAL,
	...
}

Possible-Secondary-Serving-Cell-ExtIEs NBAP-PROTOCOL-EXTENSION ::= {
	...
}

PowerAdjustmentType ::= ENUMERATED {
	none,
	common,
	individual
}

PowerOffset ::= INTEGER (0..24)
-- PowerOffset = offset * 0.25
-- Unit dB, Range 0dB .. +6dB, Step +0.25dB

PowerOffsetForSecondaryCPICHforMIMO ::= INTEGER (-6..0)
-- Unit dB, Range -6dB .. 0dB, Step +1dB

PowerRaiseLimit ::= INTEGER (0..10)

PRACH-Midamble ::= ENUMERATED {
	inverted,
	direct,
	...
}

PRC ::= INTEGER (-2047..2047)
--pseudo range correction; scaling factor 0.32 meters

PRCDeviation ::= ENUMERATED {
   one,
   two,
   five,
   ten,
   ...
}

PrecodingWeightSetRestriction ::= ENUMERATED {
	preferred,
	not-preferred
}

PreambleSignatures ::= BIT STRING {
									signature15(0),
									signature14(1),
									signature13(2),
									signature12(3),
									signature11(4),
									signature10(5),
									signature9(6),
									signature8(7),
									signature7(8),
									signature6(9),
									signature5(10),
									signature4(11),
									signature3(12),
									signature2(13),
									signature1(14),
									signature0(15)
									} (SIZE (16))

PreambleThreshold ::= INTEGER (0..72)
-- 0= -36.0dB, 1= -35.5dB, ... , 72= 0.0dB

PredictedSFNSFNDeviationLimit ::=INTEGER (1..256)
-- Unit chip, Step 1/16 chip, Range 1/16..16 chip

PredictedTUTRANGPSDeviationLimit ::= INTEGER (1..256)
-- Unit chip, Step 1/16 chip, Range 1/16..16 chip

Pre-emptionCapability ::= ENUMERATED {
	shall-not-trigger-pre-emption,
	may-trigger-pre-emption
}

Pre-emptionVulnerability ::= ENUMERATED {
	not-pre-emptable,
	pre-emptable
}

PrimaryAndSecondaryCPICHContainer ::= SEQUENCE {
	power-Offset-For-Secondary-CPICH-for-MIMO		PowerOffsetForSecondaryCPICHforMIMO,
	iE-Extensions						ProtocolExtensionContainer { { PrimaryAndSecondaryCPICHContainer-ExtIEs} } OPTIONAL,
	...
}


PrimaryAndSecondaryCPICHContainer-ExtIEs NBAP-PROTOCOL-EXTENSION ::= {
	...
}

PrimaryCPICH-Power ::= INTEGER(-100..500)
-- step 0.1 (Range -10.0..50.0) Unit is dBm

Primary-CPICH-Usage-for-Channel-Estimation ::= ENUMERATED {
primary-CPICH-may-be-used,
primary-CPICH-shall-not-be-used
}

PrimaryScramblingCode ::= INTEGER (0..511)

PriorityLevel				::= INTEGER (0..15)
-- 0 = spare, 1 = highest priority, ...14 = lowest priority and 15 = no priority

Priority-Queue-Information-for-Enhanced-FACH-PCH ::= SEQUENCE {
	priorityQueue-Id					PriorityQueue-Id,
	schedulingPriorityIndicator			SchedulingPriorityIndicator,
	t1									T1,
	mAC-ehs-Reset-Timer					MAC-ehs-Reset-Timer,
	-- shall be ignored in case of Enhanced PCH
	discardTimer						DiscardTimer							OPTIONAL,
	mAC-hsWindowSize					MAC-hsWindowSize,
	maximum-MACcPDU-Size				MAC-PDU-SizeExtended,
	iE-Extensions						ProtocolExtensionContainer { { Priority-Queue-Information-for-Enhanced-FACH-PCH-ExtIEs } }			OPTIONAL,
	...
}

Priority-Queue-Information-for-Enhanced-FACH-PCH-ExtIEs NBAP-PROTOCOL-EXTENSION ::= {
	...
}

PriorityQueue-Id ::= INTEGER (0..maxNrOfPriorityQueues-1)

PriorityQueue-InfoList ::= SEQUENCE (SIZE (1..maxNrOfPriorityQueues)) OF PriorityQueue-InfoItem

PriorityQueue-InfoItem ::= SEQUENCE {
	priorityQueueId						PriorityQueue-Id,
	associatedHSDSCH-MACdFlow			HSDSCH-MACdFlow-ID,
	schedulingPriorityIndicator			SchedulingPriorityIndicator,
	t1									T1,
	discardTimer						DiscardTimer				OPTIONAL,
	mAC-hsWindowSize					MAC-hsWindowSize,
	mAChsGuaranteedBitRate				MAChsGuaranteedBitRate										OPTIONAL,
	macdPDU-Size-Index					MACdPDU-Size-Indexlist,
	rLC-Mode							RLC-Mode,
	iE-Extensions						ProtocolExtensionContainer { { PriorityQueue-InfoItem-ExtIEs} }		OPTIONAL,
	...
}

PriorityQueue-InfoItem-ExtIEs NBAP-PROTOCOL-EXTENSION ::= {
	{ ID id-MaximumMACdPDU-SizeExtended		CRITICALITY reject		EXTENSION	MAC-PDU-SizeExtended	PRESENCE optional}|
	{ ID id-DL-RLC-PDU-Size-Format			CRITICALITY ignore		EXTENSION	DL-RLC-PDU-Size-Format		PRESENCE optional}|
	{ ID id-UE-AggregateMaximumBitRate-Enforcement-Indicator	CRITICALITY ignore	EXTENSION	UE-AggregateMaximumBitRate-Enforcement-Indicator	PRESENCE optional},
	...
}

PriorityQueue-InfoList-to-Modify ::= SEQUENCE (SIZE (1..maxNrOfPriorityQueues)) OF ModifyPriorityQueue

PriorityQueue-InfoItem-to-Add ::= SEQUENCE {
	priorityQueueId						PriorityQueue-Id,
	associatedHSDSCH-MACdFlow			HSDSCH-MACdFlow-ID,
	schedulingPriorityIndicator			SchedulingPriorityIndicator,
	t1									T1,
	discardTimer						DiscardTimer												OPTIONAL,
	mAC-hsWindowSize					MAC-hsWindowSize,
	mAChsGuaranteedBitRate				MAChsGuaranteedBitRate										OPTIONAL,
	macdPDU-Size-Index					MACdPDU-Size-Indexlist,
	rLC-Mode							RLC-Mode,
	iE-Extensions						ProtocolExtensionContainer { { PriorityQueue-InfoItem-to-Add-ExtIEs} }		OPTIONAL,
	...
}

PriorityQueue-InfoItem-to-Add-ExtIEs NBAP-PROTOCOL-EXTENSION ::= {
	{ ID id-MaximumMACdPDU-SizeExtended		CRITICALITY reject		EXTENSION	MAC-PDU-SizeExtended		PRESENCE optional} |
	{ ID id-DL-RLC-PDU-Size-Format				CRITICALITY ignore		EXTENSION	DL-RLC-PDU-Size-Format	PRESENCE optional},
	...
}

PriorityQueue-InfoItem-to-Modify ::= SEQUENCE {
	priorityQueueId						PriorityQueue-Id,
	schedulingPriorityIndicator			SchedulingPriorityIndicator									OPTIONAL,
	t1									T1															OPTIONAL,
	discardTimer						DiscardTimer												OPTIONAL,
	mAC-hsWindowSize					MAC-hsWindowSize											OPTIONAL,
	mAChsGuaranteedBitRate				MAChsGuaranteedBitRate										OPTIONAL,
	macdPDU-Size-Index-to-Modify		MACdPDU-Size-Indexlist-to-Modify							OPTIONAL,
	iE-Extensions						ProtocolExtensionContainer { { PriorityQueue-InfoItem-to-Modify-ExtIEs} }		OPTIONAL,
	...
}

PriorityQueue-InfoItem-to-Modify-ExtIEs NBAP-PROTOCOL-EXTENSION ::= {
	{ ID id-MaximumMACdPDU-SizeExtended		CRITICALITY reject		EXTENSION	MAC-PDU-SizeExtended	PRESENCE optional}|
	{ ID id-DL-RLC-PDU-Size-Format			CRITICALITY ignore		EXTENSION	DL-RLC-PDU-Size-Format	PRESENCE optional},
	...
}

PriorityQueue-InfoList-to-Modify-Unsynchronised ::= SEQUENCE (SIZE (1..maxNrOfPriorityQueues)) OF PriorityQueue-InfoItem-to-Modify-Unsynchronised

PriorityQueue-InfoItem-to-Modify-Unsynchronised ::= SEQUENCE {
	priorityQueueId						PriorityQueue-Id,
	schedulingPriorityIndicator			SchedulingPriorityIndicator															OPTIONAL,
	discardTimer						DiscardTimer																		OPTIONAL,
	mAChsGuaranteedBitRate				MAChsGuaranteedBitRate																OPTIONAL,
	iE-Extensions						ProtocolExtensionContainer { { PriorityQueue-InfoItem-to-Modify-Unsynchronised-ExtIEs} }		OPTIONAL,
	...
}

PriorityQueue-InfoItem-to-Modify-Unsynchronised-ExtIEs NBAP-PROTOCOL-EXTENSION ::= {
	...
}

PrimaryCCPCH-RSCP ::= INTEGER (0..91)
-- Mapping of non-negative values according to [23]

PrimaryCCPCH-RSCP-Delta	::= INTEGER (-5..-1,...)
-- Mapping of negative values according to [23]

PropagationDelay ::= INTEGER (0..255)
-- Unit: chips, step size 3 chips
-- example: 0 = 0chip, 1 = 3chips

PRXdes-base ::= INTEGER (-112..-50)
-- Unit: dBm, step size 1


SCH-TimeSlot ::= INTEGER (0..6)

PunctureLimit ::= INTEGER (0..15)
-- 0: 40%; 1: 44%; ... 14: 96%; 15: 100%
-- 0 is not applicable for E-DPCH

PUSCH-ID ::= INTEGER (0..255)

UE-Selected-MBMS-Service-Information ::= CHOICE {
	none							NULL,
	selected-MBMS-Service			Selected-MBMS-Service,
	...
}
Selected-MBMS-Service ::= SEQUENCE {
	selected-MBMS-Service-List				Selected-MBMS-Service-List,
	iE-Extensions							ProtocolExtensionContainer { { Selected-MBMS-Service-ExtIEs} }		OPTIONAL,
	...
}

Selected-MBMS-Service-ExtIEs  NBAP-PROTOCOL-EXTENSION ::= {
	...
}


Selected-MBMS-Service-List ::= SEQUENCE (SIZE (1.. maxMBMSServiceSelect)) OF Selected-MBMS-Service-Item


Selected-MBMS-Service-Item ::= SEQUENCE {
	selected-MBMS-Service-TimeSlot-Information-LCR			Selected-MBMS-Service-TimeSlot-Information-LCR		OPTIONAL,
	mBMS-Service-TDM-Information			MBMS-Service-TDM-Information		OPTIONAL,
	iE-Extensions							ProtocolExtensionContainer { { Selected-MBMS-Service-Item-ExtIEs} }		OPTIONAL,
	...
}

Selected-MBMS-Service-Item-ExtIEs  NBAP-PROTOCOL-EXTENSION ::= {
	...
}

Selected-MBMS-Service-TimeSlot-Information-LCR ::= SEQUENCE (SIZE (1..7)) OF TimeSlotLCR

MBMS-Service-TDM-Information ::= SEQUENCE {
	transmission-Time-Interval			ENUMERATED {v10, v20, v40, v80,...},
	tDM-Rep					INTEGER (2..9),
	tDM-Offset				INTEGER (0..8),
	tDM-Length				INTEGER (1..8),
	iE-Extensions							ProtocolExtensionContainer { { MBMS-Service-TDM-Information-ExtIEs} }		OPTIONAL,
	...
}

MBMS-Service-TDM-Information-ExtIEs  NBAP-PROTOCOL-EXTENSION ::= {
	...
}

PUSCHSet-ID ::= INTEGER (0..255)

Paging-MACFlow-Specific-InformationLCR ::= SEQUENCE (SIZE (1.. maxNrOfPagingMACFlow)) OF Paging-MAC-Flow-Specific-Information-ItemLCR

Paging-MAC-Flow-Specific-Information-ItemLCR ::= SEQUENCE {
	paging-MACFlow-Id								Paging-MACFlow-ID,
	hSDPA-associated-PICH-InfoLCR					HSDPA-Associated-PICH-InformationLCR		OPTIONAL,
	bindingID										BindingID									OPTIONAL,
	transportLayerAddress							TransportLayerAddress						OPTIONAL,
	tnl-qos											TnlQos										OPTIONAL,
	toAWS											ToAWS										OPTIONAL,
	toAWE											ToAWE										OPTIONAL,
	paging-MACFlow-PriorityQueue-InformationLCR		Paging-MACFlow-PriorityQueue-Information	OPTIONAL,
	transportBearerRequestIndicator					TransportBearerRequestIndicator				OPTIONAL,
	iE-Extensions									ProtocolExtensionContainer { { Paging-MAC-Flow-Specific-Information-ItemLCR-ExtIEs } }		OPTIONAL,
	...
}

Paging-MAC-Flow-Specific-Information-ItemLCR-ExtIEs NBAP-PROTOCOL-EXTENSION ::= {
	...
}

Paging-MACFlows-to-DeleteLCR ::= SEQUENCE (SIZE (1.. maxNrOfPagingMACFlow)) OF Paging-MACFlows-to-DeleteLCR-Item

Paging-MACFlows-to-DeleteLCR-Item ::= SEQUENCE {
	paging-MACFlow-ID								Paging-MACFlow-ID,
	iE-Extensions									ProtocolExtensionContainer { { Paging-MACFlows-to-DeleteLCR-Item-ExtIEs} }					OPTIONAL,
	...
}

Paging-MACFlows-to-DeleteLCR-Item-ExtIEs NBAP-PROTOCOL-EXTENSION ::= {
	...
}
Process-Memory-Size	::=	ENUMERATED {
										hms800, hms1600, hms2400, hms3200, hms4000,
										hms4800, hms5600, hms6400, hms7200, hms8000,
										hms8800, hms9600, hms10400, hms11200, hms12000,
										hms12800, hms13600, hms14400, hms15200, hms16000,
										hms17600, hms19200, hms20800, hms22400, hms24000,
										hms25600, hms27200, hms28800, hms30400, hms32000,
										hms36000, hms40000, hms44000, hms48000, hms52000,
										hms56000, hms60000, hms64000, hms68000, hms72000,
										hms76000, hms80000, hms88000, hms96000, hms104000,
										hms112000, hms120000, hms128000, hms136000, hms144000,
										hms152000, hms160000, hms176000, hms192000, hms208000,
										hms224000, hms240000, hms256000, hms272000, hms288000,
										hms304000,...}



-- ==========================================
--	Q
-- ==========================================

QE-Selector ::= ENUMERATED {
	selected,
	non-selected
}

-- ==========================================
--	R
-- ==========================================

RACH-Measurement-Result ::= ENUMERATED {
	cpich-EcNo,
	cpich-RSCP,
	pathloss,
	...
}

RACH-SlotFormat ::= ENUMERATED {
	v0,
	v1,
	v2,
	v3,
	...
}

RACH-SubChannelNumbers ::= BIT STRING {
										subCh11(0),
										subCh10(1),
									 	subCh9(2),
									 	subCh8(3),
									 	subCh7(4),
									 	subCh6(5),
									 	subCh5(6),
									 	subCh4(7),
									 	subCh3(8),
									 	subCh2(9),
									 	subCh1(10),
									 	subCh0(11)
										} (SIZE (12))

RL-Specific-DCH-Info ::= SEQUENCE (SIZE (1..maxNrOfDCHs)) OF RL-Specific-DCH-Info-Item

RL-Specific-DCH-Info-Item ::= SEQUENCE {
	dCH-id					DCH-ID,
	bindingID				BindingID															OPTIONAL,
	transportlayeraddress	TransportLayerAddress												OPTIONAL,
	iE-Extensions			ProtocolExtensionContainer { { RL-Specific-DCH-Info-Item-ExtIEs} }	OPTIONAL,
	...
}

RL-Specific-DCH-Info-Item-ExtIEs NBAP-PROTOCOL-EXTENSION ::= {
	{ ID id-TransportBearerNotRequestedIndicator	CRITICALITY ignore	EXTENSION TransportBearerNotRequestedIndicator		PRESENCE optional	}, -- FDD only
	...
}

RL-Specific-E-DCH-Info ::= SEQUENCE {
	rL-Specific-E-DCH-Information		RL-Specific-E-DCH-Information,
	e-AGCH-PowerOffset					E-AGCH-PowerOffset							OPTIONAL,
	e-RGCH-PowerOffset					E-RGCH-PowerOffset							OPTIONAL,
	e-HICH-PowerOffset					E-HICH-PowerOffset							OPTIONAL,
	iE-Extensions			ProtocolExtensionContainer { { RL-Specific-E-DCH-Info-Item-ExtIEs} }	OPTIONAL,
	...
}

RL-Specific-E-DCH-Info-Item-ExtIEs NBAP-PROTOCOL-EXTENSION ::= {
	...
}


RL-Specific-E-DCH-Information ::= SEQUENCE (SIZE (1..maxNrOfEDCHMACdFlows)) OF RL-Specific-E-DCH-Information-Item

RL-Specific-E-DCH-Information-Item ::= SEQUENCE {
	e-DCH-MACdFlow-ID		E-DCH-MACdFlow-ID,
	bindingID				BindingID									OPTIONAL,
	transportlayeraddress	TransportLayerAddress						OPTIONAL,
	iE-Extensions			ProtocolExtensionContainer { { RL-Specific-E-DCH-Information-Item-ExtIEs} }	OPTIONAL,
	...
}

RL-Specific-E-DCH-Information-Item-ExtIEs NBAP-PROTOCOL-EXTENSION ::= {
	...
}

Range-Correction-Rate ::= INTEGER (-127..127)
-- scaling factor 0.032 m/s

Reference-ReceivedTotalWideBandPower ::= INTEGER (0..621)
-- mapping as for RTWP measurement value, as specified in [22]


Reference-ReceivedTotalWideBandPowerReporting::= ENUMERATED {
	reference-ReceivedTotalWideBandPower-Requested
}

Reference-ReceivedTotalWideBandPowerSupportIndicator::= ENUMERATED {
	indication-of-Reference-ReceivedTotalWideBandPower-supported
}

ReferenceClockAvailability ::= ENUMERATED {
	available,
	notAvailable
}

ReferenceSFNoffset ::= INTEGER (0..255)

Reference-E-TFCI-Information ::= SEQUENCE (SIZE (1..maxNrOfRefETFCIs)) OF Reference-E-TFCI-Information-Item

Reference-E-TFCI-Information-Item ::= SEQUENCE {
	reference-E-TFCI				E-TFCI,
	-- The following IE shall be ignored if id-Ext-Reference-E-TFCI-PO is present in Reference-E-TFCI-Information-Item-ExtIEs
	reference-E-TFCI-PO				Reference-E-TFCI-PO,
	iE-Extensions					ProtocolExtensionContainer { { Reference-E-TFCI-Information-Item-ExtIEs} }		OPTIONAL,
	...
}

Reference-E-TFCI-Information-Item-ExtIEs NBAP-PROTOCOL-EXTENSION ::= {
	-- The following IE shall be present if the ref E-TFCI power offset to be signalled exceeds maxNrOfRefETFCI-PO-QUANTSTEPs
	{ ID id-Ext-Reference-E-TFCI-PO		CRITICALITY reject		EXTENSION	Ext-Reference-E-TFCI-PO		PRESENCE optional},
	...
}

Reference-E-TFCI-PO ::= INTEGER (0.. maxNrOfRefETFCI-PO-QUANTSTEPs)

RepetitionLength ::= INTEGER (1..63)

RepetitionPeriod ::= ENUMERATED {
	v1,
	v2,
	v4,
	v8,
	v16,
	v32,
	v64,
	...
}

RepetitionNumber0 ::= INTEGER (0..255)

RepetitionNumber1 ::= INTEGER (1..256)

RefTFCNumber ::= INTEGER (0..3)

ReportCharacteristics ::= CHOICE {
	onDemand			NULL,
	periodic			ReportCharacteristicsType-ReportPeriodicity,
	event-a				ReportCharacteristicsType-EventA,
	event-b				ReportCharacteristicsType-EventB,
	event-c				ReportCharacteristicsType-EventC,
	event-d				ReportCharacteristicsType-EventD,
	event-e				ReportCharacteristicsType-EventE,
	event-f				ReportCharacteristicsType-EventF,
	...,
	extension-ReportCharacteristics		Extension-ReportCharacteristics
}

Extension-ReportCharacteristics	::= ProtocolIE-Single-Container {{ Extension-ReportCharacteristicsIE }}

Extension-ReportCharacteristicsIE NBAP-PROTOCOL-IES ::= {
	{ ID id-ReportCharacteristicsType-OnModification	CRITICALITY reject	TYPE ReportCharacteristicsType-OnModification		PRESENCE mandatory }
}

ReportCharacteristicsType-EventA ::= SEQUENCE {
	measurementThreshold			ReportCharacteristicsType-MeasurementThreshold,
	measurementHysteresisTime		ReportCharacteristicsType-ScaledMeasurementHysteresisTime			OPTIONAL,
	iE-Extensions					ProtocolExtensionContainer { { ReportCharacteristicsType-EventA-ExtIEs} }		OPTIONAL,
	...
	}

ReportCharacteristicsType-EventA-ExtIEs NBAP-PROTOCOL-EXTENSION ::= {
	...
}

ReportCharacteristicsType-EventB ::= SEQUENCE {
	measurementThreshold			ReportCharacteristicsType-MeasurementThreshold,
	measurementHysteresisTime		ReportCharacteristicsType-ScaledMeasurementHysteresisTime			OPTIONAL,
	iE-Extensions					ProtocolExtensionContainer { { ReportCharacteristicsType-EventB-ExtIEs} }		OPTIONAL,
	...
	}

ReportCharacteristicsType-EventB-ExtIEs NBAP-PROTOCOL-EXTENSION ::= {
	...
}

ReportCharacteristicsType-EventC ::= SEQUENCE {
	measurementIncreaseThreshold	ReportCharacteristicsType-MeasurementIncreaseDecreaseThreshold,
	measurementChangeTime			ReportCharacteristicsType-ScaledMeasurementChangeTime,
	iE-Extensions					ProtocolExtensionContainer { { ReportCharacteristicsType-EventC-ExtIEs} }		OPTIONAL,
	...
	}

ReportCharacteristicsType-EventC-ExtIEs NBAP-PROTOCOL-EXTENSION ::= {
	...
}

ReportCharacteristicsType-EventD ::= SEQUENCE {
	measurementDecreaseThreshold	ReportCharacteristicsType-MeasurementIncreaseDecreaseThreshold,
	measurementChangeTime			ReportCharacteristicsType-ScaledMeasurementChangeTime,
	iE-Extensions					ProtocolExtensionContainer { { ReportCharacteristicsType-EventD-ExtIEs} }		OPTIONAL,
	...
	}

ReportCharacteristicsType-EventD-ExtIEs NBAP-PROTOCOL-EXTENSION ::= {
	...
}

ReportCharacteristicsType-EventE ::= SEQUENCE {
	measurementThreshold1			ReportCharacteristicsType-MeasurementThreshold,
	measurementThreshold2			ReportCharacteristicsType-MeasurementThreshold				OPTIONAL,
	measurementHysteresisTime		ReportCharacteristicsType-ScaledMeasurementHysteresisTime	OPTIONAL,
	reportPeriodicity				ReportCharacteristicsType-ReportPeriodicity					OPTIONAL,
	iE-Extensions					ProtocolExtensionContainer { { ReportCharacteristicsType-EventE-ExtIEs} }		OPTIONAL,
	...
	}

ReportCharacteristicsType-EventE-ExtIEs NBAP-PROTOCOL-EXTENSION ::= {
	...
}

ReportCharacteristicsType-EventF ::= SEQUENCE {
	measurementThreshold1			ReportCharacteristicsType-MeasurementThreshold,
	measurementThreshold2			ReportCharacteristicsType-MeasurementThreshold				OPTIONAL,
	measurementHysteresisTime		ReportCharacteristicsType-ScaledMeasurementHysteresisTime	OPTIONAL,
	reportPeriodicity				ReportCharacteristicsType-ReportPeriodicity					OPTIONAL,
	iE-Extensions					ProtocolExtensionContainer { { ReportCharacteristicsType-EventF-ExtIEs} }		OPTIONAL,
	...
	}

ReportCharacteristicsType-EventF-ExtIEs NBAP-PROTOCOL-EXTENSION ::= {
	...
}

ReportCharacteristicsType-OnModification ::= SEQUENCE {
	measurementThreshold			ReportCharacteristicsType-MeasurementThreshold,
	iE-Extensions					ProtocolExtensionContainer { { ReportCharacteristicsType-OnModification-ExtIEs} }		OPTIONAL,
		...
	}

ReportCharacteristicsType-OnModification-ExtIEs NBAP-PROTOCOL-EXTENSION ::= {
	...
}

ReportCharacteristicsType-MeasurementIncreaseDecreaseThreshold ::= CHOICE {
	received-total-wide-band-power							Received-total-wide-band-power-Value-IncrDecrThres,
	transmitted-carrier-power		Transmitted-Carrier-Power-Value,
	acknowledged-prach-preambles			Acknowledged-PRACH-preambles-Value,
	uL-TimeslotISCP					UL-TimeslotISCP-Value-IncrDecrThres,
	sir							SIR-Value-IncrDecrThres,
	sir-error					SIR-Error-Value-IncrDecrThres,
	transmitted-code-power			Transmitted-Code-Power-Value-IncrDecrThres,
	rscp							RSCP-Value-IncrDecrThres,
	round-trip-time					Round-Trip-Time-IncrDecrThres,
	notUsed-1-acknowledged-PCPCH-access-preambles		NULL,
	notUsed-2-detected-PCPCH-access-preambles			NULL,
	...,
	extension-ReportCharacteristicsType-MeasurementIncreaseDecreaseThreshold		Extension-ReportCharacteristicsType-MeasurementIncreaseDecreaseThreshold
}

Extension-ReportCharacteristicsType-MeasurementIncreaseDecreaseThreshold	::= ProtocolIE-Single-Container {{ Extension-ReportCharacteristicsType-MeasurementIncreaseDecreaseThresholdIE }}

Extension-ReportCharacteristicsType-MeasurementIncreaseDecreaseThresholdIE NBAP-PROTOCOL-IES ::= {
{ ID id-TransmittedCarrierPowerOfAllCodesNotUsedForHSTransmission			CRITICALITY reject	TYPE TransmittedCarrierPowerOfAllCodesNotUsedForHSTransmissionValue PRESENCE mandatory}|
{ ID id-Transmitted-Carrier-Power-For-CellPortion		CRITICALITY reject	TYPE Transmitted-Carrier-Power-Value		PRESENCE mandatory }|
{ ID id-Received-total-wide-band-power-For-CellPortion	CRITICALITY reject	TYPE Received-total-wide-band-power-Value-IncrDecrThres		PRESENCE mandatory }|
{ ID id-TransmittedCarrierPowerOfAllCodesNotUsedForHS-PDSCH-HS-SCCH-E-AGCH-E-RGCHOrE-HICHTransmissionCellPortion	CRITICALITY reject	TYPE TransmittedCarrierPowerOfAllCodesNotUsedForHSTransmissionValue		PRESENCE mandatory }|
{ ID id-UpPTSInterferenceValue		CRITICALITY reject	TYPE 	UpPTSInterferenceValue					PRESENCE mandatory }|
{ ID id-Received-Scheduled-EDCH-Power-Share		CRITICALITY reject	TYPE RSEPS-Value-IncrDecrThres		PRESENCE mandatory }|
{ ID id-Received-Scheduled-EDCH-Power-Share-For-CellPortion	CRITICALITY reject	TYPE RSEPS-Value-IncrDecrThres		PRESENCE mandatory }|
{ ID id-EDCH-RACH-Report-IncrDecrThres						CRITICALITY reject	TYPE EDCH-RACH-Report-IncrDecrThres		PRESENCE mandatory }|
	-- FDD only
{ ID id-TransmittedCarrierPowerOfAllCodesNotUsedForHS-PDSCH-HS-SCCH-E-AGCHOrE-HICHTransmissionCellPortion	CRITICALITY reject	TYPE TransmittedCarrierPowerOfAllCodesNotUsedForHSTransmissionValue		PRESENCE mandatory }|
{ ID id-ULTimeslotISCPValue-For-CellPortion		CRITICALITY reject	TYPE 	UL-TimeslotISCP-Value-IncrDecrThres					PRESENCE mandatory }|
{ ID id-UpPTSInterferenceValue-For-CellPortion		CRITICALITY reject	TYPE 	UpPTSInterferenceValue					PRESENCE mandatory }
}

EDCH-RACH-Report-IncrDecrThres ::= SEQUENCE {
	denied-EDCH-RACH-resources		Denied-EDCH-RACH-Resources-Value,
	iE-Extensions		ProtocolExtensionContainer { { EDCH-RACH-Report-IncrDecrThres-ExtIEs } } OPTIONAL,
		...
}

EDCH-RACH-Report-IncrDecrThres-ExtIEs NBAP-PROTOCOL-EXTENSION ::= {
	...
}

Granted-EDCH-RACH-Resources-Value ::= INTEGER(0..240,...)
-- According to mapping in [25].

Denied-EDCH-RACH-Resources-Value ::= INTEGER(0..240,...)
-- According to mapping in [25].

ReportCharacteristicsType-MeasurementThreshold ::= CHOICE {
	received-total-wide-band-power							Received-total-wide-band-power-Value,
	transmitted-carrier-power		Transmitted-Carrier-Power-Value,
	acknowledged-prach-preambles			Acknowledged-PRACH-preambles-Value,
	uL-TimeslotISCP					UL-TimeslotISCP-Value,
	sir							SIR-Value,
	sir-error					SIR-Error-Value,
	transmitted-code-power			Transmitted-Code-Power-Value,
	rscp							RSCP-Value,
	rx-timing-deviation				Rx-Timing-Deviation-Value,
	round-trip-time					Round-Trip-Time-Value,
	notUsed-1-acknowledged-PCPCH-access-preambles		NULL,
	notUsed-2-detected-PCPCH-access-preambles			NULL,
	...,
	extension-ReportCharacteristicsType-MeasurementThreshold		Extension-ReportCharacteristicsType-MeasurementThreshold
}

Extension-ReportCharacteristicsType-MeasurementThreshold	::= ProtocolIE-Single-Container {{ Extension-ReportCharacteristicsType-MeasurementThresholdIE }}

Extension-ReportCharacteristicsType-MeasurementThresholdIE NBAP-PROTOCOL-IES ::= {
	{ ID id-TUTRANGPSMeasurementThresholdInformation	CRITICALITY reject	TYPE TUTRANGPSMeasurementThresholdInformation		PRESENCE mandatory }|
	{ ID id-SFNSFNMeasurementThresholdInformation		CRITICALITY reject	TYPE SFNSFNMeasurementThresholdInformation			PRESENCE mandatory }|
	{ ID id-Rx-Timing-Deviation-Value-LCR				CRITICALITY reject	TYPE Rx-Timing-Deviation-Value-LCR				PRESENCE mandatory}|
	{ ID id-HS-SICH-Reception-Quality-Measurement-Value	CRITICALITY reject	TYPE HS-SICH-Reception-Quality-Measurement-Value	PRESENCE mandatory}|
	-- For 1.28Mcps TDD, used when the Measurement Threshold Value for HS-SICH Reception Quality are less than or equal to 20
	{ ID id-TransmittedCarrierPowerOfAllCodesNotUsedForHSTransmission CRITICALITY reject	TYPE TransmittedCarrierPowerOfAllCodesNotUsedForHSTransmissionValue PRESENCE mandatory}|
	{ ID id-HS-DSCHRequiredPowerValue					CRITICALITY reject	TYPE HS-DSCHRequiredPowerValue				PRESENCE mandatory}|
	{ ID id-Transmitted-Carrier-Power-For-CellPortion	CRITICALITY reject	TYPE Transmitted-Carrier-Power-Value				PRESENCE mandatory }|
	{ ID id-Received-total-wide-band-power-For-CellPortion	CRITICALITY reject	TYPE Received-total-wide-band-power-Value 	PRESENCE mandatory }|
	{ ID id-TransmittedCarrierPowerOfAllCodesNotUsedForHS-PDSCH-HS-SCCH-E-AGCH-E-RGCHOrE-HICHTransmissionCellPortion	 CRITICALITY reject	TYPE TransmittedCarrierPowerOfAllCodesNotUsedForHSTransmissionValue		PRESENCE mandatory }|
	{ ID id-UpPTSInterferenceValue						CRITICALITY reject	TYPE UpPTSInterferenceValue				PRESENCE mandatory }|
	{ ID id-DLTransmissionBranchLoadValue				CRITICALITY reject	TYPE DLTransmissionBranchLoadValue					PRESENCE mandatory }|
	{ ID id-HS-DSCHRequiredPowerValue-For-Cell-Portion	CRITICALITY reject	TYPE HS-DSCHRequiredPowerValue							PRESENCE mandatory }|
	{ ID id-E-DCH-Non-serving-Relative-Grant-Down-CommandsValue		CRITICALITY reject	TYPE E-DCH-Non-serving-Relative-Grant-Down-Commands			PRESENCE mandatory }|
	{ ID id-Rx-Timing-Deviation-Value-768				CRITICALITY reject	TYPE Rx-Timing-Deviation-Value-768				PRESENCE mandatory }|
	{ ID id-Rx-Timing-Deviation-Value-384-ext			CRITICALITY reject	TYPE Rx-Timing-Deviation-Value-384-ext				PRESENCE mandatory }|
	{ ID id-Extended-Round-Trip-Time-Value					CRITICALITY reject	TYPE Extended-Round-Trip-Time-Value				PRESENCE mandatory }|
	{ ID id-Received-Scheduled-EDCH-Power-Share					CRITICALITY reject	TYPE RSEPS-Value-IncrDecrThres				PRESENCE mandatory }|
	{ ID id-Received-Scheduled-EDCH-Power-Share-For-CellPortion	CRITICALITY reject	TYPE RSEPS-Value-IncrDecrThres				PRESENCE mandatory }|
	{ ID id-Additional-HS-SICH-Reception-Quality-Measurement-Value	CRITICALITY reject	TYPE HS-SICH-Reception-Quality-Measurement-Value			PRESENCE mandatory}|
	-- Applicable to 1.28Mcps TDD only, used when the Measurement Threshold Value for HS-SICH Reception Quality are more than 20, Measurement Threshold Value = 20 + IE Value
	{ ID id-TUTRANGANSSMeasurementThresholdInformation	CRITICALITY reject	TYPE TUTRANGANSSMeasurementThresholdInformation	PRESENCE mandatory }|
	{ ID id-EDCH-RACH-Report-ThresholdInformation		CRITICALITY reject	TYPE EDCH-RACH-Report-ThresholdInformation			PRESENCE mandatory }|
	-- FDD only
	{ ID id-TransmittedCarrierPowerOfAllCodesNotUsedForHS-PDSCH-HS-SCCH-E-AGCHOrE-HICHTransmissionCellPortion	CRITICALITY reject	TYPE TransmittedCarrierPowerOfAllCodesNotUsedForHSTransmissionValue		PRESENCE mandatory }|
	{ ID id-ULTimeslotISCPValue-For-CellPortion			CRITICALITY reject	TYPE 	UL-TimeslotISCP-Value				PRESENCE mandatory }|
	{ ID id-UpPTSInterferenceValue-For-CellPortion		CRITICALITY reject	TYPE 	UpPTSInterferenceValue				PRESENCE mandatory }
}

EDCH-RACH-Report-ThresholdInformation ::= SEQUENCE {
	denied-EDCH-RACH-resources		Denied-EDCH-RACH-Resources-Value,
	iE-Extensions		ProtocolExtensionContainer { { EDCH-RACH-Report-ThresholdInformation-ExtIEs } } OPTIONAL,
		...
}

EDCH-RACH-Report-ThresholdInformation-ExtIEs NBAP-PROTOCOL-EXTENSION ::= {
	...
}

ReportCharacteristicsType-ScaledMeasurementChangeTime ::= CHOICE {
	msec				MeasurementChangeTime-Scaledmsec,
	...
}

MeasurementChangeTime-Scaledmsec ::= INTEGER (1..6000,...)
-- MeasurementChangeTime-Scaledmsec = Time * 10
-- Unit ms, Range 10ms .. 60000ms(1min), Step 10ms

ReportCharacteristicsType-ScaledMeasurementHysteresisTime ::= CHOICE {
	msec				MeasurementHysteresisTime-Scaledmsec,
	...
}

MeasurementHysteresisTime-Scaledmsec ::= INTEGER (1..6000,...)
-- MeasurementHysteresisTime-Scaledmsec = Time * 10
-- Unit ms, Range 10ms .. 60000ms(1min), Step 10ms

ReportCharacteristicsType-ReportPeriodicity ::= CHOICE {
	msec 				ReportPeriodicity-Scaledmsec,
	min					ReportPeriodicity-Scaledmin,
	...
}

ReportPeriodicity-Scaledmsec ::= INTEGER (1..6000,...)
-- ReportPeriodicity-msec = ReportPeriodicity * 10
-- Unit ms, Range 10ms .. 60000ms(1min), Step 10ms

ReportPeriodicity-Scaledmin ::= INTEGER (1..60,...)
-- Unit min, Range 1min .. 60min(hour), Step 1min

ReportPeriodicity-Scaledhour ::= INTEGER (1..24,...)
-- Unit hour, Range 1hour .. 24hours(day), Step 1hour

ResourceOperationalState ::= ENUMERATED {
	enabled,
	disabled
}

RL-ID ::= INTEGER (0..31)

RL-Set-ID				::= INTEGER (0..31)

RLC-Mode	::= ENUMERATED {
	rLC-AM,
	rLC-UM,
	...
}

DL-RLC-PDU-Size-Format	::= ENUMERATED {
	fixed-RLC-PDU-Size,
	flexible-RLC-PDU-Size,
	...
}

Round-Trip-Time-IncrDecrThres ::= INTEGER(0..32766)

RNC-ID					::= INTEGER (0..4095)

Round-Trip-Time-Value ::= INTEGER(0..32767)
-- According to mapping in [22]

RSCP-Value ::= INTEGER (0..127)
-- According to mapping in [23]

RSCP-Value-IncrDecrThres ::= INTEGER (0..126)

Received-total-wide-band-power-For-CellPortion-Value ::= SEQUENCE (SIZE (1..maxNrOfCellPortionsPerCell)) OF Received-total-wide-band-power-For-CellPortion-Value-Item

Received-total-wide-band-power-For-CellPortion-Value-Item ::= SEQUENCE{
	cellPortionID							CellPortionID,
	received-total-wide-band-power-value	Received-total-wide-band-power-Value,
	iE-Extensions							ProtocolExtensionContainer { { Received-total-wide-band-power-For-CellPortion-Value-Item-ExtIEs} }		OPTIONAL,
...
}

Received-total-wide-band-power-For-CellPortion-Value-Item-ExtIEs NBAP-PROTOCOL-EXTENSION ::= {
	...
}

Received-total-wide-band-power-For-CellPortion-ValueLCR ::= SEQUENCE (SIZE (1..maxNrOfCellPortionsPerCellLCR)) OF Received-total-wide-band-power-For-CellPortion-ValueLCR-Item

Received-total-wide-band-power-For-CellPortion-ValueLCR-Item ::= SEQUENCE{
	cellPortionLCRID							CellPortionLCRID,
	received-total-wide-band-power-value	Received-total-wide-band-power-Value,
	iE-Extensions							ProtocolExtensionContainer { { Received-total-wide-band-power-For-CellPortion-ValueLCR-Item-ExtIEs} }		OPTIONAL,
...
}

Received-total-wide-band-power-For-CellPortion-ValueLCR-Item-ExtIEs NBAP-PROTOCOL-EXTENSION ::= {
	...
}

Received-total-wide-band-power-Value ::= INTEGER(0..621)
-- According to mapping in [22]/[23]

Received-total-wide-band-power-Value-IncrDecrThres ::= INTEGER (0..620)

Received-Scheduled-EDCH-Power-Share-For-CellPortion-Value ::= SEQUENCE (SIZE (1..maxNrOfCellPortionsPerCell)) OF Received-Scheduled-EDCH-Power-Share-For-CellPortion-Value-Item

Received-Scheduled-EDCH-Power-Share-For-CellPortion-Value-Item ::= SEQUENCE{
	cellPortionID							CellPortionID,
	received-Scheduled-power-share-value	RSEPS-Value,
	received-total-wide-band-power-value	Received-total-wide-band-power-Value		OPTIONAL,
	iE-Extensions							ProtocolExtensionContainer { { Received-Scheduled-EDCH-Power-Share-For-CellPortion-Value-Item-ExtIEs} }		OPTIONAL,
	...
	}

Received-Scheduled-EDCH-Power-Share-For-CellPortion-Value-Item-ExtIEs NBAP-PROTOCOL-EXTENSION ::= {
	...
}

Received-Scheduled-EDCH-Power-Share-Value ::= SEQUENCE{
	received-Scheduled-power-share-value	RSEPS-Value,
	received-total-wide-band-power-value	Received-total-wide-band-power-Value		OPTIONAL,
	...
	}

RSEPS-Value-IncrDecrThres ::= INTEGER (0..151)


RSEPS-Value ::= INTEGER (0..151)
-- According to mapping in [22]


RequestedDataValueInformation ::= CHOICE {
	informationAvailable		InformationAvailable,
	informationnotAvailable		InformationnotAvailable
}

InformationAvailable::= SEQUENCE {
	requesteddataValue		RequestedDataValue,
	ie-Extensions			ProtocolExtensionContainer { { InformationAvailableItem-ExtIEs} }		OPTIONAL,
	...
}

InformationAvailableItem-ExtIEs NBAP-PROTOCOL-EXTENSION ::= {
	...
}

InformationnotAvailable ::= NULL

RequestedDataValue ::= SEQUENCE {
	dgps-corrections		DGPSCorrections													OPTIONAL,
	gps-navandrecovery		GPS-NavigationModel-and-TimeRecovery							OPTIONAL,
	gps-ionos-model			GPS-Ionospheric-Model											OPTIONAL,
	gps-utc-model			GPS-UTC-Model													OPTIONAL,
	gps-almanac				GPS-Almanac														OPTIONAL,
	gps-rt-integrity		GPS-RealTime-Integrity											OPTIONAL,
	gpsrxpos				GPS-RX-POS														OPTIONAL,
	iE-Extensions			ProtocolExtensionContainer { { RequestedDataValue-ExtIEs} }		OPTIONAL,
	...
}

RequestedDataValue-ExtIEs NBAP-PROTOCOL-EXTENSION ::= {
	{ ID id-GANSS-Common-Data			CRITICALITY ignore		EXTENSION GANSS-Common-Data				PRESENCE optional }|
	{ ID id-GANSS-Generic-Data			CRITICALITY ignore		EXTENSION GANSS-Generic-Data									PRESENCE optional },
	...
}

Rx-Timing-Deviation-Value ::= INTEGER (0..8191)
-- According to mapping in [23]

Rx-Timing-Deviation-Value-LCR ::= INTEGER (0..511)
-- According to mapping in [23]

Rx-Timing-Deviation-Value-768 ::= INTEGER (0..65535)
-- According to mapping in [23]

Rx-Timing-Deviation-Value-384-ext ::= INTEGER (0..32767)
-- According to mapping in [23]

RefBeta ::= INTEGER (-15..16)

RTWP-ReportingIndicator ::= ENUMERATED {
	rTWP-reporting-required}

RTWP-CellPortion-ReportingIndicator ::= ENUMERATED {
	rTWP-CellPortion-reporting-required}


-- ==========================================
--	S
-- ==========================================

AdjustmentPeriod			::= INTEGER(1..256)
-- Unit Frame

E-DPCCH-Power-Boosting-Capability ::= ENUMERATED {
	e-DPCCH-Power-Boosting-capable,
	e-DPCCH-Power-Boosting-non-capable
}

SAT-ID ::= INTEGER (0..63)

SAT-Info-Almanac ::= SEQUENCE (SIZE (1..maxNoSat)) OF SAT-Info-Almanac-Item

SAT-Info-Almanac-Item ::= SEQUENCE {
	data-id			   DATA-ID,
    sat-id             SAT-ID,
    gps-e-alm          BIT STRING (SIZE (16)),
    gps-toa-alm        BIT STRING (SIZE (8)),
    gps-delta-I-alm    BIT STRING (SIZE (16)),
    omegadot-alm       BIT STRING (SIZE (16)),
    svhealth-alm       BIT STRING (SIZE (8)),
    gps-a-sqrt-alm     BIT STRING (SIZE (24)),
    omegazero-alm      BIT STRING (SIZE (24)),
    m-zero-alm         BIT STRING (SIZE (24)),
    gps-omega-alm      BIT STRING (SIZE (24)),
    gps-af-zero-alm    BIT STRING (SIZE (11)),
    gps-af-one-alm     BIT STRING (SIZE (11)),
    ie-Extensions	   ProtocolExtensionContainer { { SAT-Info-Almanac-Item-ExtIEs} }		OPTIONAL,
   ...
}	-- This GPS-Almanac-Information is for the 1st 16 satellites

SAT-Info-Almanac-Item-ExtIEs NBAP-PROTOCOL-EXTENSION ::= {
	...
}

SAT-Info-Almanac-ExtList	::= SEQUENCE (SIZE (1..maxNrOfSatAlmanac-maxNoSat)) OF SAT-Info-Almanac-ExtItem

SAT-Info-Almanac-ExtItem	::= SEQUENCE {
	data-id			   DATA-ID,
    sat-id             SAT-ID,
    gps-e-alm          BIT STRING (SIZE (16)),
    gps-toa-alm        BIT STRING (SIZE (8)),
    gps-delta-I-alm    BIT STRING (SIZE (16)),
    omegadot-alm       BIT STRING (SIZE (16)),
    svhealth-alm       BIT STRING (SIZE (8)),
    gps-a-sqrt-alm     BIT STRING (SIZE (24)),
    omegazero-alm      BIT STRING (SIZE (24)),
    m-zero-alm         BIT STRING (SIZE (24)),
    gps-omega-alm      BIT STRING (SIZE (24)),
    gps-af-zero-alm    BIT STRING (SIZE (11)),
    gps-af-one-alm     BIT STRING (SIZE (11)),
    ie-Extensions	   ProtocolExtensionContainer { { SAT-Info-Almanac-ExtItemIEs } }		OPTIONAL,
   ...
}	--	Includes the GPS-Almanac-Information for 17th through 32nd satellites.

SAT-Info-Almanac-ExtItemIEs NBAP-PROTOCOL-EXTENSION ::= {
	...
}

SAT-Info-DGPSCorrections ::= SEQUENCE (SIZE (1..maxNoSat)) OF SAT-Info-DGPSCorrections-Item

SAT-Info-DGPSCorrections-Item ::= SEQUENCE {
    sat-id                                	SAT-ID,
    iode-dgps                           	BIT STRING (SIZE (8)),
    udre            						UDRE,
    prc             						PRC,
    range-correction-rate             		Range-Correction-Rate,
    ie-Extensions							ProtocolExtensionContainer { { SAT-Info-DGPSCorrections-Item-ExtIEs} }  OPTIONAL,
   ...
}

SAT-Info-DGPSCorrections-Item-ExtIEs NBAP-PROTOCOL-EXTENSION ::= {
	{ID id-DGNSS-ValidityPeriod	CRITICALITY	ignore	EXTENSION	DGNSS-ValidityPeriod	PRESENCE	optional},
	...
}

SATInfo-RealTime-Integrity ::= SEQUENCE (SIZE (1..maxNoSat)) OF SAT-Info-RealTime-Integrity-Item

SAT-Info-RealTime-Integrity-Item ::= SEQUENCE {
  bad-sat-id       SAT-ID,
  ie-Extensions	   ProtocolExtensionContainer { { SAT-Info-RealTime-Integrity-Item-ExtIEs} }		OPTIONAL,
   ...
}

SAT-Info-RealTime-Integrity-Item-ExtIEs NBAP-PROTOCOL-EXTENSION ::= {
	...
}

ScaledAdjustmentRatio			::= INTEGER(0..100)
-- AdjustmentRatio  = ScaledAdjustmentRatio / 100

MaxAdjustmentStep			::= INTEGER(1..10)
-- Unit Slot

SchedulingInformation 			::= ENUMERATED {
	included,
	not-included
}

SecondaryServingCells ::= SEQUENCE (SIZE (1..maxNrOfHSDSCH-1)) OF SecondaryServingCellsItem

SecondaryServingCellsItem ::= SEQUENCE {
	secondaryC-ID				C-ID,
	numSecondaryHS-SCCH-Codes		NumHS-SCCH-Codes		OPTIONAL,
	sixtyfourQAM-UsageAllowedIndicator		SixtyfourQAM-UsageAllowedIndicator 		OPTIONAL,
	iE-Extensions									ProtocolExtensionContainer { { SecondaryServingCellsItem-ExtIEs} }				OPTIONAL,
	...
}

SecondaryServingCellsItem-ExtIEs NBAP-PROTOCOL-EXTENSION ::= {
	{ID	id-MIMO-ActivationIndicator			CRITICALITY ignore		EXTENSION MIMO-ActivationIndicator	PRESENCE optional}|
{ID	id-EDCH-Indicator			CRITICALITY ignore		EXTENSION NULL		PRESENCE optional},
	...
}

Secondary-UL-Frequency-Activation-State ::= ENUMERATED {
	activated,
	deactivated,
		...
}

SchedulingPriorityIndicator 			::= INTEGER (0..15)		 -- lowest (0), highest (15)

SID ::= INTEGER (0..maxNrOfMACdPDUIndexes-1)

ScramblingCodeNumber ::= INTEGER (0..15)

Secondary-CPICH-Information-Change ::= CHOICE {
	new-secondary-CPICH					CommonPhysicalChannelID,
	secondary-CPICH-shall-not-be-used	NULL,
...
}

SecondaryCCPCH-SlotFormat ::= INTEGER(0..17,...)

Secondary-CCPCH-SlotFormat-Extended ::= INTEGER(18..23,...)

Segment-Type ::= ENUMERATED {
		first-segment,
		first-segment-short,
		subsequent-segment,
		last-segment,
		last-segment-short,
		complete-SIB,
		complete-SIB-short,
		...
}

Serving-E-DCH-RL-ID ::= CHOICE {
	serving-E-DCH-RL-in-this-NodeB				Serving-E-DCH-RL-in-this-NodeB,
	serving-E-DCH-RL-not-in-this-NodeB			NULL,
	...
}

Serving-E-DCH-RL-in-this-NodeB ::= SEQUENCE {
	rL-ID										RL-ID,
	iE-Extensions								ProtocolExtensionContainer { { Serving-E-DCH-RL-in-this-NodeB-ExtIEs} }			OPTIONAL,
	...
}

Serving-E-DCH-RL-in-this-NodeB-ExtIEs NBAP-PROTOCOL-EXTENSION ::= {
	...
}

SetsOfHS-SCCH-Codes ::= SEQUENCE (SIZE (1..maxNrOfHSDSCH)) OF SetsOfHS-SCCH-CodesItem

SetsOfHS-SCCH-CodesItem ::= SEQUENCE {
	hS-SCCH-PreconfiguredCodes		HS-SCCH-PreconfiguredCodes,
	sixtyfourQAM-DL-UsageIndicator		SixtyfourQAM-DL-UsageIndicator		OPTIONAL,
	hSDSCH-TBSizeTableIndicator		HSDSCH-TBSizeTableIndicator				OPTIONAL,
	iE-Extensions					ProtocolExtensionContainer { { SetsOfHS-SCCH-CodesItem-ExtIEs} } OPTIONAL,
	...
}

SetsOfHS-SCCH-CodesItem-ExtIEs NBAP-PROTOCOL-EXTENSION ::= {
	{ID	id-MIMO-N-M-Ratio				CRITICALITY ignore		EXTENSION MIMO-N-M-Ratio			PRESENCE optional},
	...
}

Setup-Or-ConfigurationChange-Or-Removal-Of-EDCH-On-secondary-UL-Frequency::= CHOICE {
	setup					Additional-EDCH-Setup-Info,
	configurationChange		Additional-EDCH-Cell-Information-ConfigurationChange-List,
	removal					Additional-EDCH-Cell-Information-Removal-List,
	...
}

SFN ::= INTEGER (0..4095)

SFNSFN-FDD ::= INTEGER (0..614399)

SFNSFN-TDD ::= INTEGER (0..40961)

SFNSFN-TDD768 ::= INTEGER (0..81923)

SFNSFNChangeLimit ::= INTEGER (1..256)
-- Unit chip, Step 1/16 chip, Range 1/16..16 chip

SFNSFNDriftRate ::= INTEGER (-100..100)
-- Unit chip/s, Step 1/256 chip/s, Range -100/256..+100/256 chip/s

SFNSFNDriftRateQuality ::= INTEGER (0..100)
-- Unit chip/s, Step 1/256 chip/s, Range 0..100/256 chip/s

SFNSFNMeasurementThresholdInformation::= SEQUENCE {
	sFNSFNChangeLimit					SFNSFNChangeLimit					OPTIONAL,
	predictedSFNSFNDeviationLimit		PredictedSFNSFNDeviationLimit		OPTIONAL,
	iE-Extensions					ProtocolExtensionContainer { { SFNSFNMeasurementThresholdInformation-ExtIEs} }		OPTIONAL,
	...
}

SFNSFNMeasurementThresholdInformation-ExtIEs NBAP-PROTOCOL-EXTENSION ::= {
	...
}

SFNSFNMeasurementValueInformation ::= SEQUENCE {
	successfullNeighbouringCellSFNSFNObservedTimeDifferenceMeasurementInformation		SEQUENCE (SIZE(1..maxNrOfMeasNCell)) OF
		SEQUENCE {
			uC-Id						UC-Id,
			sFNSFNValue					SFNSFNValue,
			sFNSFNQuality				SFNSFNQuality				OPTIONAL,
			sFNSFNDriftRate				SFNSFNDriftRate,
			sFNSFNDriftRateQuality		SFNSFNDriftRateQuality		OPTIONAL,
			sFNSFNTimeStampInformation	SFNSFNTimeStampInformation,
			iE-Extensions		ProtocolExtensionContainer { { SuccessfullNeighbouringCellSFNSFNObservedTimeDifferenceMeasurementInformationItem-ExtIEs} }		OPTIONAL,
			...
		},
	unsuccessfullNeighbouringCellSFNSFNObservedTimeDifferenceMeasurementInformation		SEQUENCE (SIZE(0..maxNrOfMeasNCell-1)) OF
		SEQUENCE {
			uC-Id						UC-Id,
			iE-Extensions		ProtocolExtensionContainer { { UnsuccessfullNeighbouringCellSFNSFNObservedTimeDifferenceMeasurementInformationItem-ExtIEs} }		OPTIONAL,
				...
		},
	iE-Extensions		ProtocolExtensionContainer { { SFNSFNMeasurementValueInformationItem-ExtIEs} }		OPTIONAL,
	...
}

SFNSFNMeasurementValueInformationItem-ExtIEs NBAP-PROTOCOL-EXTENSION ::= {
	...
}

SuccessfullNeighbouringCellSFNSFNObservedTimeDifferenceMeasurementInformationItem-ExtIEs NBAP-PROTOCOL-EXTENSION ::= {
	...
}

UnsuccessfullNeighbouringCellSFNSFNObservedTimeDifferenceMeasurementInformationItem-ExtIEs NBAP-PROTOCOL-EXTENSION ::= {
	...
}

SFNSFNQuality ::= INTEGER (0..255)
-- Unit chip, Step 1/16 chip, Range 0.. 255/16 chip

ShutdownTimer ::= INTEGER (1..3600)
-- Unit sec

SIB-Originator ::= ENUMERATED {
	nodeB,
	cRNC,
	...
}

SIR-Error-Value ::= INTEGER (0..125)
-- According to mapping in [22]

SFNSFNTimeStampInformation ::= CHOICE {
	sFNSFNTimeStamp-FDD		SFN,
	sFNSFNTimeStamp-TDD		SFNSFNTimeStamp-TDD,
	...}

SFNSFNTimeStamp-TDD::= SEQUENCE {
	sFN					SFN,
	timeSlot			TimeSlot,
	iE-Extensions					ProtocolExtensionContainer { { SFNSFNTimeStamp-ExtIEs} }		OPTIONAL,
	...
}

SFNSFNTimeStamp-ExtIEs NBAP-PROTOCOL-EXTENSION ::= {
	...
}

SFNSFNValue ::= CHOICE {
	sFNSFN-FDD		SFNSFN-FDD,
	sFNSFN-TDD		SFNSFN-TDD,			--- 1.28Mcps and 3.84Mcps TDD only
	...,
	sFNSFN-TDD768	SFNSFN-TDD768
}

Single-Stream-MIMO-ActivationIndicator ::= NULL

Single-Stream-MIMO-Capability ::= ENUMERATED {
	single-stream-mimo-capable,
	single-stream-mimo-non-capable
}


Single-Stream-MIMO-Mode-Indicator ::= ENUMERATED {
	activate,
	deactivate
}

SIR-Error-Value-IncrDecrThres ::= INTEGER (0..124)

SIR-Value ::= INTEGER (0..63)
-- According to mapping in [22]/[23]

SIR-Value-IncrDecrThres ::= INTEGER (0..62)

SignallingBearerRequestIndicator::= ENUMERATED {bearerRequested}


SixtyfourQAM-UsageAllowedIndicator ::= ENUMERATED {
	allowed,
	not-allowed
}

SixtyfourQAM-DL-UsageIndicator ::= ENUMERATED {
	sixtyfourQAM-DL-used,
	sixtyfourQAM-DL-not-used
}

SixtyfourQAM-DL-Capability ::= ENUMERATED {
	sixtyfourQAM-DL-supported,
	sixtyfourQAM-DL-not-supported
}

SixtyfourQAM-DL-MIMO-Combined-Capability ::= ENUMERATED {
	sixtyfourQAM-DL-MIMO-Combined-capable,
	sixtyfourQAM-DL-MIMO-Combined-non-capable
}

SignatureSequenceGroupIndex ::= INTEGER (0..19)


SixteenQAM-UL-Capability ::= ENUMERATED {
	sixteenQAM-UL-capable,
	sixteenQAM-UL-non-capable
}

SixteenQAM-UL-Operation-Indicator ::= ENUMERATED {
	activate,
	deactivate
}


SNPL-Reporting-Type ::= ENUMERATED {
	type1,
	type2
}

Soffset ::= INTEGER (0..9,...)

SpecialBurstScheduling ::= INTEGER (1..256)	-- Number of frames between special burst transmission during DTX

Start-Of-Audit-Sequence-Indicator ::= ENUMERATED {
	start-of-audit-sequence,
	not-start-of-audit-sequence
}

Status-Flag ::= ENUMERATED {
	activate,
	deactivate
}

STTD-Indicator ::= ENUMERATED {
	active,
	inactive,
	...
}

SSDT-SupportIndicator ::= ENUMERATED {
	not-Used-sSDT-Supported,
	sSDT-not-supported
}

Sub-Frame-Number ::= INTEGER (0..4,...)

SyncCase ::= INTEGER (1..2,...)

SYNCDlCodeId ::= INTEGER (1..32,...)

SyncFrameNumber ::= INTEGER (1..10)

SynchronisationReportCharacteristics ::= SEQUENCE {
	synchronisationReportCharacteristicsType	SynchronisationReportCharacteristicsType,
	synchronisationReportCharactThreExc			SynchronisationReportCharactThreExc		OPTIONAL,
		-- This IE shall be included if the synchronisationReportCharacteristicsType IE is set to "thresholdExceeding".
	iE-Extensions								ProtocolExtensionContainer { { SynchronisationReportCharacteristics-ExtIEs } }	OPTIONAL,
	...
}

SynchronisationReportCharacteristics-ExtIEs	NBAP-PROTOCOL-EXTENSION ::= {
	{ ID id-SyncDLCodeIdThreInfoLCR	CRITICALITY	ignore EXTENSION	SyncDLCodeIdThreInfoLCR		PRESENCE optional },
	...
}

SynchronisationReportCharactThreExc ::= 	SEQUENCE (SIZE (1..maxNrOfCellSyncBursts)) OF SynchronisationReportCharactThreInfoItem  -- Mandatory for 3.84Mcps TDD only. Not Applicable to 1.28Mcps TDD.

SynchronisationReportCharactThreInfoItem ::= SEQUENCE {
	syncFrameNumber				SyncFrameNumber,
	cellSyncBurstInformation	SEQUENCE (SIZE (1.. maxNrOfReceptsPerSyncFrame)) OF SynchronisationReportCharactCellSyncBurstInfoItem,
	iE-Extensions				ProtocolExtensionContainer { { SynchronisationReportCharactThreInfoItem-ExtIEs } }		OPTIONAL,
	...
}

SynchronisationReportCharactThreInfoItem-ExtIEs NBAP-PROTOCOL-EXTENSION ::= {
	...
}

SynchronisationReportCharactCellSyncBurstInfoItem ::= SEQUENCE {
	cellSyncBurstCode 				CellSyncBurstCode,
	cellSyncBurstCodeShift 			CellSyncBurstCodeShift,
	cellSyncBurstTiming 			CellSyncBurstTiming				OPTIONAL,
	cellSyncBurstTimingThreshold 	CellSyncBurstTimingThreshold	OPTIONAL,
	iE-Extensions					ProtocolExtensionContainer { { SynchronisationReportCharactCellSyncBurstInfoItem-ExtIEs } }		OPTIONAL,
	...
}

SynchronisationReportCharactCellSyncBurstInfoItem-ExtIEs NBAP-PROTOCOL-EXTENSION ::= {
	...
}

SyncDLCodeIdThreInfoLCR ::= SEQUENCE (SIZE (0..maxNrOfSyncFramesLCR)) OF SyncDLCodeIdThreInfoList  --Mandatory for 1.28Mcps TDD only. Not Applicable to 3.84Mcps TDD.

SyncDLCodeIdThreInfoList ::= SEQUENCE {
	syncFrameNoToReceive			SyncFrameNumber,
	syncDLCodeIdInfoLCR				SyncDLCodeInfoListLCR,
	iE-Extensions					ProtocolExtensionContainer { { SyncDLCodeIdThreInfoList-ExtIEs } }		OPTIONAL,
	...
}

SyncDLCodeIdThreInfoList-ExtIEs NBAP-PROTOCOL-EXTENSION ::= {
	...
}

SyncDLCodeInfoListLCR ::= SEQUENCE (SIZE (1..maxNrOfSyncDLCodesLCR)) OF SyncDLCodeInfoItemLCR

SyncDLCodeInfoItemLCR ::= SEQUENCE {
	syncDLCodeId					SYNCDlCodeId,
	syncDLCodeIdArrivTime			CellSyncBurstTimingLCR				OPTIONAL,
	syncDLCodeIdTimingThre			CellSyncBurstTimingThreshold		OPTIONAL,
	iE-Extensions					ProtocolExtensionContainer { { SyncDLCodeInfoItem-LCR-ExtIEs } }		OPTIONAL,
	...
}

SyncDLCodeInfoItem-LCR-ExtIEs NBAP-PROTOCOL-EXTENSION ::= {
	...
}

SynchronisationReportCharacteristicsType ::= ENUMERATED {
	frameRelated,
	sFNperiodRelated,
	cycleLengthRelated,
	thresholdExceeding,
	frequencyAcquisitionCompleted,
	...
}

SynchronisationReportType ::= ENUMERATED {
	initialPhase,
	steadyStatePhase,
	lateEntrantCell,
	frequencyAcquisition,
	...
}
Semi-PersistentScheduling-CapabilityLCR ::= ENUMERATED {
	semi-Persistent-scheduling-Capable,
	semi-Persistent-scheduling-Non-Capable
}

-- ==========================================
--	T
-- ==========================================

T1 ::= ENUMERATED {v10,v20,v30,v40,v50,v60,v70,v80,v90,v100,v120,v140,v160,v200,v300,v400,...}

T321 ::= ENUMERATED {v100,v200,v400,v800,...}

T-Cell ::= ENUMERATED {
	v0,
	v1,
	v2,
	v3,
	v4,
	v5,
	v6,
	v7,
	v8,
	v9
}

T-RLFAILURE ::= INTEGER (0..255)
-- Unit seconds, Range 0s .. 25.5s, Step 0.1s

T-PROTECT ::= ENUMERATED {v40,v60,v80,v100,v120,v200,v400,...}
T-SYNC ::= ENUMERATED {v40,v80,v120,v160,v200,v300,v400,v500,...}

TDD-AckNack-Power-Offset ::= INTEGER (-7..8,...)
-- Unit dB, Range -7dB .. +8dB, Step 1dB

TDD-ChannelisationCode ::= ENUMERATED {
	chCode1div1,
	chCode2div1,
	chCode2div2,
	chCode4div1,
	chCode4div2,
	chCode4div3,
	chCode4div4,
	chCode8div1,
	chCode8div2,
	chCode8div3,
	chCode8div4,
	chCode8div5,
	chCode8div6,
	chCode8div7,
	chCode8div8,
	chCode16div1,
	chCode16div2,
	chCode16div3,
	chCode16div4,
	chCode16div5,
	chCode16div6,
	chCode16div7,
	chCode16div8,
	chCode16div9,
	chCode16div10,
	chCode16div11,
	chCode16div12,
	chCode16div13,
	chCode16div14,
	chCode16div15,
	chCode16div16,
	...
}

TDD-ChannelisationCodeLCR ::= SEQUENCE {
	tDD-ChannelisationCode			TDD-ChannelisationCode,
	modulation						Modulation, -- Modulation options for 1.28Mcps TDD in contrast to 3.84Mcps TDD or 7.68Mcps TDD
	iE-Extensions							ProtocolExtensionContainer { { TDD-ChannelisationCodeLCR-ExtIEs} }		OPTIONAL,
	...
}

TDD-ChannelisationCodeLCR-ExtIEs NBAP-PROTOCOL-EXTENSION ::= {
	...
}


TDD-ChannelisationCode768 			::= ENUMERATED {
	chCode1div1,
	chCode2div1,
	chCode2div2,
	chCode4div1,
	chCode4div2,
	chCode4div3,
	chCode4div4,
	chCode8div1,
	chCode8div2,
	chCode8div3,
	chCode8div4,
	chCode8div5,
	chCode8div6,
	chCode8div7,
	chCode8div8,
	chCode16div1,
	chCode16div2,
	chCode16div3,
	chCode16div4,
	chCode16div5,
	chCode16div6,
	chCode16div7,
	chCode16div8,
	chCode16div9,
	chCode16div10,
	chCode16div11,
	chCode16div12,
	chCode16div13,
	chCode16div14,
	chCode16div15,
	chCode16div16,
	chCode32div1,
	chCode32div2,
	chCode32div3,
	chCode32div4,
	chCode32div5,
	chCode32div6,
	chCode32div7,
	chCode32div8,
	chCode32div9,
	chCode32div10,
	chCode32div11,
	chCode32div12,
	chCode32div13,
	chCode32div14,
	chCode32div15,
	chCode32div16,
	chCode32div17,
	chCode32div18,
	chCode32div19,
	chCode32div20,
	chCode32div21,
	chCode32div22,
	chCode32div23,
	chCode32div24,
	chCode32div25,
	chCode32div26,
	chCode32div27,
	chCode32div28,
	chCode32div29,
	chCode32div30,
	chCode32div31,
	chCode32div32,
	...
}

TDD-DL-Code-Information ::= SEQUENCE (SIZE (1..maxNrOfDPCHs)) OF TDD-DL-Code-InformationItem

TDD-DL-Code-InformationItem	 ::= SEQUENCE {
	dPCH-ID									DPCH-ID,
	tdd-ChannelisationCode					TDD-ChannelisationCode,
	iE-Extensions							ProtocolExtensionContainer { { TDD-DL-Code-InformationItem-ExtIEs} }		OPTIONAL,
	...
}

TDD-DL-Code-InformationItem-ExtIEs NBAP-PROTOCOL-EXTENSION ::= {
	...
}

TDD-DL-Code-LCR-Information ::= SEQUENCE (SIZE (1..maxNrOfDPCHLCRs)) OF TDD-DL-Code-LCR-InformationItem

TDD-DL-Code-LCR-InformationItem ::= SEQUENCE {
	dPCH-ID									DPCH-ID,
	tdd-ChannelisationCodeLCR				TDD-ChannelisationCodeLCR,
	tdd-DL-DPCH-TimeSlotFormat-LCR			TDD-DL-DPCH-TimeSlotFormat-LCR,
	iE-Extensions							ProtocolExtensionContainer { { TDD-DL-Code-LCR-InformationItem-ExtIEs} }		OPTIONAL,
	...
}

TDD-DL-Code-LCR-InformationItem-ExtIEs NBAP-PROTOCOL-EXTENSION ::= {
	...
}

TDD-DL-Code-768-Information ::= SEQUENCE (SIZE (1..maxNrOfDPCHs768)) OF TDD-DL-Code-768-InformationItem

TDD-DL-Code-768-InformationItem	 ::= SEQUENCE {
	dPCH-ID									DPCH-ID,
	tdd-ChannelisationCode768				TDD-ChannelisationCode768,
	iE-Extensions							ProtocolExtensionContainer { { TDD-DL-Code-768-InformationItem-ExtIEs} }		OPTIONAL,
	...
}

TDD-DL-Code-768-InformationItem-ExtIEs NBAP-PROTOCOL-EXTENSION ::= {
	...
}

TDD-DL-DPCH-TimeSlotFormat-LCR ::= CHOICE {
	qPSK						QPSK-DL-DPCH-TimeSlotFormatTDD-LCR,
	eightPSK					EightPSK-DL-DPCH-TimeSlotFormatTDD-LCR,
	-- For 1.28 Mcps TDD, if the cell is operating in MBSFN only mode, this IE denotes MBSFN S-CCPCH time slot format
	...
}

QPSK-DL-DPCH-TimeSlotFormatTDD-LCR ::= INTEGER(0..24,...)

EightPSK-DL-DPCH-TimeSlotFormatTDD-LCR ::= INTEGER(0..24,...)
-- For 1.28 Mcps TDD, if the cell is operating in MBSFN only mode, this IE denotes MBSFN S-CCPCH time slot format?INTEGER(0..11,...)

TDD-DPCHOffset ::= CHOICE {
	initialOffset		INTEGER (0..255),
	noinitialOffset		INTEGER (0..63)
}

TDD-PhysicalChannelOffset ::= INTEGER (0..63)

TDD-TPC-DownlinkStepSize ::= ENUMERATED {
	step-size1,
	step-size2,
	step-size3,
	...
}

TDD-TPC-UplinkStepSize-LCR ::= ENUMERATED {
	step-size1,
	step-size2,
	step-size3,
	...
}

TransportFormatCombination-Beta ::= CHOICE {
	signalledGainFactors		SEQUENCE {
		gainFactor					CHOICE {
			fdd							SEQUENCE {
				betaC						BetaCD,
				betaD						BetaCD,
				iE-Extensions		ProtocolExtensionContainer { { GainFactorFDD-ExtIEs } }		OPTIONAL,
				...
			},
			tdd							BetaCD,
			...
		},
	    refTFCNumber				RefTFCNumber	OPTIONAL,
		iE-Extensions			ProtocolExtensionContainer { { SignalledGainFactors-ExtIEs } }		OPTIONAL,
		...
	},
	computedGainFactors				RefTFCNumber,
	...
}

GainFactorFDD-ExtIEs NBAP-PROTOCOL-EXTENSION ::= {
	...
}

SignalledGainFactors-ExtIEs NBAP-PROTOCOL-EXTENSION ::= {
	...
}

TDD-UL-Code-Information ::= SEQUENCE (SIZE (1..maxNrOfDPCHs)) OF TDD-UL-Code-InformationItem

TDD-UL-Code-InformationItem ::= SEQUENCE {
	dPCH-ID									DPCH-ID,
	tdd-ChannelisationCode					TDD-ChannelisationCode,
	iE-Extensions							ProtocolExtensionContainer { { TDD-UL-Code-InformationItem-ExtIEs} }		OPTIONAL,
	...
}

TDD-UL-Code-InformationItem-ExtIEs NBAP-PROTOCOL-EXTENSION ::= {
	...
}

TDD-UL-Code-LCR-Information ::= SEQUENCE (SIZE (1..maxNrOfDPCHLCRs)) OF TDD-UL-Code-LCR-InformationItem

TDD-UL-Code-LCR-InformationItem ::= SEQUENCE {
	dPCH-ID									DPCH-ID,
	tdd-ChannelisationCodeLCR				TDD-ChannelisationCodeLCR,
	tdd-UL-DPCH-TimeSlotFormat-LCR			TDD-UL-DPCH-TimeSlotFormat-LCR,
	iE-Extensions							ProtocolExtensionContainer { { TDD-UL-Code-LCR-InformationItem-ExtIEs} }		OPTIONAL,
	...
}

TDD-UL-Code-LCR-InformationItem-ExtIEs NBAP-PROTOCOL-EXTENSION ::= {
	...
}
TDD-UL-Code-768-Information ::= SEQUENCE (SIZE (1..maxNrOfDPCHs)) OF TDD-UL-Code-768-InformationItem

TDD-UL-Code-768-InformationItem ::= SEQUENCE {
	dPCH-ID									DPCH-ID,
	tdd-ChannelisationCode768				TDD-ChannelisationCode768,
	iE-Extensions							ProtocolExtensionContainer { { TDD-UL-Code-768-InformationItem-ExtIEs} }		OPTIONAL,
	...
}

TDD-UL-Code-768-InformationItem-ExtIEs NBAP-PROTOCOL-EXTENSION ::= {
	...
}

TDD-UL-DPCH-TimeSlotFormat-LCR ::= CHOICE {
	qPSK						QPSK-UL-DPCH-TimeSlotFormatTDD-LCR,
	eightPSK					EightPSK-UL-DPCH-TimeSlotFormatTDD-LCR,
	...
}

QPSK-UL-DPCH-TimeSlotFormatTDD-LCR ::= INTEGER(0..69,...)

EightPSK-UL-DPCH-TimeSlotFormatTDD-LCR ::= INTEGER(0..24,...)

TFCI-Coding ::= ENUMERATED {
	v4,
	v8,
	v16,
	v32,
	...
}

TFCI-Presence ::= ENUMERATED {
	present,
	not-present
}

TFCI-SignallingMode ::= SEQUENCE {
	tFCI-SignallingOption		TFCI-SignallingMode-TFCI-SignallingOption,
	not-Used-splitType			NULL				OPTIONAL,
	not-Used-lengthOfTFCI2		NULL				OPTIONAL,
	iE-Extensions				ProtocolExtensionContainer { { TFCI-SignallingMode-ExtIEs} }		OPTIONAL,
	...
}

TFCI-SignallingMode-ExtIEs NBAP-PROTOCOL-EXTENSION ::= {
	...
}

TFCI-SignallingMode-TFCI-SignallingOption ::= ENUMERATED {
	normal,
	not-Used-split
}

TGD					::= INTEGER (0|15..269)
-- 0 = Undefined, only one transmission gap in the transmission gap pattern sequence

TGPRC 				::= INTEGER (0..511)
-- 0 = infinity

TGPSID				::= INTEGER (1.. maxTGPS)

TGSN				::= INTEGER (0..14)

TimeSlot ::= INTEGER (0..14)

TimeSlotDirection ::= ENUMERATED {
	ul,
	dl,
	...
}

TimeSlot-InitiatedListLCR ::= SEQUENCE (SIZE (0..6)) OF TimeSlotLCR

TimeSlotLCR ::= INTEGER (0..6)

TimeslotLCR-Extension ::= ENUMERATED {
	ts7,
	...
}
-- ts7 indicates the MBSFN Special Timeslot for 1.28Mcps TDD MBSFN Dedicated Carrier.

TimeSlotMeasurementValueListLCR::= SEQUENCE (SIZE (1..6)) OF TimeSlotMeasurementValueLCR

TimeSlotMeasurementValueLCR ::= SEQUENCE {
	timeSlotLCR					TimeSlotLCR,
	commonMeasurementValue		CommonMeasurementValue,
	iE-Extensions				ProtocolExtensionContainer { {TimeSlotMeasurementValueListLCR-ExtIEs} } OPTIONAL,
	...
}

TimeSlotMeasurementValueListLCR-ExtIEs NBAP-PROTOCOL-EXTENSION ::= {
	...
}

TimeSlotStatus ::= ENUMERATED {
	active,
	not-active,
	...
}

TimingAdjustmentValue ::= CHOICE {
	initialPhase		INTEGER (0..1048575,...),
	steadyStatePhase	INTEGER (0..255,...)
}

TimingAdjustmentValueLCR ::= CHOICE {
	initialPhase		INTEGER (0..524287,...),
	steadyStatePhase	INTEGER (0..127,...)
}

TimingAdvanceApplied ::= ENUMERATED {
	yes,
	no
}

SynchronisationIndicator ::= ENUMERATED {
	timingMaintainedSynchronisation,
	...
}

TnlQos ::= CHOICE {
	dsField					DsField,
	genericTrafficCategory	GenericTrafficCategory,
	...
}

ToAWE ::= INTEGER (0..2559)
-- Unit ms

ToAWS ::= INTEGER (0..1279)
-- Unit ms

Transmission-Gap-Pattern-Sequence-Information ::= SEQUENCE (SIZE (1..maxTGPS)) OF
	SEQUENCE {
		tGPSID			TGPSID,
		tGSN			TGSN,
		tGL1			GapLength,
		tGL2			GapLength	OPTIONAL,
		tGD				TGD,
		tGPL1			GapDuration,
		not-to-be-used-1			GapDuration	OPTIONAL,
			-- This IE shall never be included in the SEQUENCE. If received it shall be ignored
		uL-DL-mode		UL-DL-mode,
		downlink-Compressed-Mode-Method		Downlink-Compressed-Mode-Method		OPTIONAL,
			-- This IE shall be present if the UL/DL mode IE is set to "DL only" or "UL/DL"
		uplink-Compressed-Mode-Method		Uplink-Compressed-Mode-Method		OPTIONAL,
			-- This IE shall be present if the UL/DL mode IE is set to "UL only" or "UL/DL"
		dL-FrameType		DL-FrameType,
		delta-SIR1			DeltaSIR,
		delta-SIR-after1	DeltaSIR,
		delta-SIR2			DeltaSIR	OPTIONAL,
		delta-SIR-after2	DeltaSIR	OPTIONAL,
		iE-Extensions			ProtocolExtensionContainer { {Transmission-Gap-Pattern-Sequence-Information-ExtIEs} } OPTIONAL,
		...
	}

Transmission-Gap-Pattern-Sequence-Information-ExtIEs NBAP-PROTOCOL-EXTENSION ::= {
	...
}

TransmissionGapPatternSequenceCodeInformation	::= ENUMERATED{
code-change,
nocode-change
}

TransmittedCarrierPowerOfAllCodesNotUsedForHS-PDSCH-HS-SCCH-E-AGCH-E-RGCHOrE-HICHTransmissionCellPortionValue ::= SEQUENCE (SIZE (1..maxNrOfCellPortionsPerCell)) OF TransmittedCarrierPowerOfAllCodesNotUsedForHS-PDSCH-HS-SCCH-E-AGCH-E-RGCHOrE-HICHTransmissionCellPortionValue-Item

TransmittedCarrierPowerOfAllCodesNotUsedForHS-PDSCH-HS-SCCH-E-AGCH-E-RGCHOrE-HICHTransmissionCellPortionValue-Item ::= SEQUENCE{
	cellPortionID							CellPortionID,
	transmittedCarrierPowerOfAllCodesNotUsedForHSTransmissionValue	TransmittedCarrierPowerOfAllCodesNotUsedForHSTransmissionValue,
	iE-Extensions							ProtocolExtensionContainer { { TransmittedCarrierPowerOfAllCodesNotUsedForHS-PDSCH-HS-SCCH-E-AGCH-E-RGCHOrE-HICHTransmissionCellPortionValue-Item-ExtIEs} }		OPTIONAL,
	...
}

TransmittedCarrierPowerOfAllCodesNotUsedForHS-PDSCH-HS-SCCH-E-AGCH-E-RGCHOrE-HICHTransmissionCellPortionValue-Item-ExtIEs NBAP-PROTOCOL-EXTENSION ::= {
	...
}

TransmittedCarrierPowerOfAllCodesNotUsedForHS-PDSCH-HS-SCCH-E-AGCHOrE-HICHTransmissionCellPortionValue ::= SEQUENCE (SIZE (1..maxNrOfCellPortionsPerCellLCR)) OF TransmittedCarrierPowerOfAllCodesNotUsedForHS-PDSCH-HS-SCCH-E-AGCHOrE-HICHTransmissionCellPortionValue-Item

TransmittedCarrierPowerOfAllCodesNotUsedForHS-PDSCH-HS-SCCH-E-AGCHOrE-HICHTransmissionCellPortionValue-Item ::= SEQUENCE{
	cellPortionLCRID							CellPortionLCRID,
	transmittedCarrierPowerOfAllCodesNotUsedForHSTransmissionValue	TransmittedCarrierPowerOfAllCodesNotUsedForHSTransmissionValue,
	iE-Extensions							ProtocolExtensionContainer { { TransmittedCarrierPowerOfAllCodesNotUsedForHS-PDSCH-HS-SCCH-E-AGCHOrE-HICHTransmissionCellPortionValue-Item-ExtIEs} }		OPTIONAL,
	...
}

TransmittedCarrierPowerOfAllCodesNotUsedForHS-PDSCH-HS-SCCH-E-AGCHOrE-HICHTransmissionCellPortionValue-Item-ExtIEs NBAP-PROTOCOL-EXTENSION ::= {
	...
}

TransmittedCarrierPowerOfAllCodesNotUsedForHSTransmissionValue ::= INTEGER(0..100)
-- According to mapping in [22] and [23]

Transmitted-Carrier-Power-For-CellPortion-Value ::= SEQUENCE (SIZE (1..maxNrOfCellPortionsPerCell)) OF Transmitted-Carrier-Power-For-CellPortion-Value-Item

Transmitted-Carrier-Power-For-CellPortion-Value-Item ::= SEQUENCE{
	cellPortionID							CellPortionID,
	transmitted-Carrier-Power-Value			Transmitted-Carrier-Power-Value,
	iE-Extensions							ProtocolExtensionContainer { { Transmitted-Carrier-Power-For-CellPortion-Value-Item-ExtIEs} }		OPTIONAL,
	...
}

Transmitted-Carrier-Power-For-CellPortion-Value-Item-ExtIEs NBAP-PROTOCOL-EXTENSION ::= {
	...
}

Transmitted-Carrier-Power-For-CellPortion-ValueLCR ::= SEQUENCE (SIZE (1..maxNrOfCellPortionsPerCellLCR)) OF Transmitted-Carrier-Power-For-CellPortion-ValueLCR-Item

Transmitted-Carrier-Power-For-CellPortion-ValueLCR-Item ::= SEQUENCE{
	cellPortionLCRID							CellPortionLCRID,
	transmitted-Carrier-Power-Value			Transmitted-Carrier-Power-Value,
	iE-Extensions							ProtocolExtensionContainer { { Transmitted-Carrier-Power-For-CellPortion-ValueLCR-Item-ExtIEs} }		OPTIONAL,
	...
}

Transmitted-Carrier-Power-For-CellPortion-ValueLCR-Item-ExtIEs NBAP-PROTOCOL-EXTENSION ::= {
	...
}

Transmitted-Carrier-Power-Value ::= INTEGER(0..100)
-- According to mapping in [22]/[23]

Transmitted-Code-Power-Value ::= INTEGER (0..127)
-- According to mapping in [22]/[23]. Values 0 to 9 and 123 to 127 shall not be used.

Transmitted-Code-Power-Value-IncrDecrThres ::= INTEGER (0..112,...)

TransmissionDiversityApplied ::= BOOLEAN
-- true: applied, false: not applied

TransmitDiversityIndicator ::= ENUMERATED {
	active,
	inactive
}

TFCS ::= SEQUENCE {
	tFCSvalues					CHOICE {
		no-Split-in-TFCI			TFCS-TFCSList,
		not-Used-split-in-TFCI		NULL,
		-- This choice shall never be made by the CRNC and the Node B shall consider the procedure as failed if it is received.
		...
	},
	iE-Extensions		ProtocolExtensionContainer  { { TFCS-ExtIEs} }		OPTIONAL,
	...
}

TFCS-ExtIEs NBAP-PROTOCOL-EXTENSION ::= {
	...
}

TFCS-TFCSList ::= SEQUENCE (SIZE (1..maxNrOfTFCs)) OF
	SEQUENCE {
		cTFC				TFCS-CTFC,
		tFC-Beta		TransportFormatCombination-Beta 	OPTIONAL,
		-- The IE shall be present if the TFCS concerns a UL DPCH or PRACH channel [FDD - or PCPCH channel].
		iE-Extensions		ProtocolExtensionContainer  { { TFCS-TFCSList-ExtIEs} }		OPTIONAL,
		...
}

TFCS-TFCSList-ExtIEs NBAP-PROTOCOL-EXTENSION ::= {
	...
}

TFCS-CTFC ::= CHOICE {
	ctfc2bit							INTEGER (0..3),
	ctfc4bit							INTEGER (0..15),
	ctfc6bit							INTEGER (0..63),
	ctfc8bit							INTEGER (0..255),
	ctfc12bit							INTEGER (0..4095),
	ctfc16bit							INTEGER (0..65535),
	ctfcmaxbit							INTEGER (0..maxCTFC)
}

Transport-Block-Size-Index ::= INTEGER(1..maxNrOfHS-DSCH-TBSs)

Transport-Block-Size-Index-for-Enhanced-PCH ::= INTEGER(1..32)
-- Index of the value range 1 to 32 of the MAC-ehs transport block size as specified in appendix A of [32]

Transport-Block-Size-List ::= SEQUENCE (SIZE (1..maxNrOfHS-DSCHTBSsE-PCH)) OF
	SEQUENCE {
		transport-Block-Size-Index-for-Enhanced-PCH			Transport-Block-Size-Index-for-Enhanced-PCH,
		iE-Extensions				ProtocolExtensionContainer  { { Transport-Block-Size-List-ExtIEs} }		OPTIONAL,
		...
	}

Transport-Block-Size-List-ExtIEs NBAP-PROTOCOL-EXTENSION ::= {
	...
}

TransportBearerRequestIndicator ::= ENUMERATED {
	bearerRequested,
	bearerNotRequested,
	...
}

TransportBearerNotRequestedIndicator ::= ENUMERATED {
	transport-bearer-shall-not-be-established,
	transport-bearer-may-not-be-established
}

TransportBearerNotSetupIndicator ::= ENUMERATED {
	transport-bearer-not-setup
}

TransportFormatSet ::= SEQUENCE {
	dynamicParts			TransportFormatSet-DynamicPartList,
	semi-staticPart			TransportFormatSet-Semi-staticPart,
	iE-Extensions			ProtocolExtensionContainer  { { TransportFormatSet-ExtIEs} }		OPTIONAL,
	...
}

TransportFormatSet-ExtIEs NBAP-PROTOCOL-EXTENSION ::= {
	...
}

TransportFormatSet-DynamicPartList ::= SEQUENCE (SIZE (1..maxNrOfTFs)) OF
	SEQUENCE {
		nrOfTransportBlocks			TransportFormatSet-NrOfTransportBlocks,
		transportBlockSize			TransportFormatSet-TransportBlockSize		OPTIONAL,
		-- This IE shall be present if the Number of Transport Blocks IE is set to a value greater than 0
		mode						TransportFormatSet-ModeDP,
		iE-Extensions				ProtocolExtensionContainer  { { TransportFormatSet-DynamicPartList-ExtIEs} }		OPTIONAL,
		...
	}

TransportFormatSet-DynamicPartList-ExtIEs NBAP-PROTOCOL-EXTENSION ::= {
	...
}

TDD-TransportFormatSet-ModeDP ::= SEQUENCE {
	transmissionTimeIntervalInformation		TransmissionTimeIntervalInformation		OPTIONAL,
	-- This IE shall be present if the Transmission Time Interval IE in the Semi-static Transport Format Information IE is set to "dynamic"
	iE-Extensions							ProtocolExtensionContainer { {TDD-TransportFormatSet-ModeDP-ExtIEs} } OPTIONAL,
	...
	}

TDD-TransportFormatSet-ModeDP-ExtIEs NBAP-PROTOCOL-EXTENSION ::= {
	...
}

TransmissionTimeIntervalInformation ::= SEQUENCE (SIZE (1..maxTTI-count)) OF
	SEQUENCE {
		transmissionTimeInterval		TransportFormatSet-TransmissionTimeIntervalDynamic,
	iE-Extensions						ProtocolExtensionContainer { { TransmissionTimeIntervalInformation-ExtIEs} }		OPTIONAL,
	...
}

TransmissionTimeIntervalInformation-ExtIEs NBAP-PROTOCOL-EXTENSION ::= {
	...
}

TransportFormatSet-Semi-staticPart ::= SEQUENCE {
	transmissionTimeInterval	 		TransportFormatSet-TransmissionTimeIntervalSemiStatic,
	channelCoding					TransportFormatSet-ChannelCodingType,
	codingRate						TransportFormatSet-CodingRate				OPTIONAL,
	-- This IE shall be present if the Type of channel coding IE is set to 'convolutional' or 'turbo'
	rateMatchingAttribute			TransportFormatSet-RateMatchingAttribute,
	cRC-Size						TransportFormatSet-CRC-Size,
	mode							TransportFormatSet-ModeSSP	,
	iE-Extensions					ProtocolExtensionContainer { { TransportFormatSet-Semi-staticPart-ExtIEs} }		OPTIONAL,
	...
}

TransportFormatSet-Semi-staticPart-ExtIEs NBAP-PROTOCOL-EXTENSION ::= {
	...
}

TransportFormatSet-ChannelCodingType ::= ENUMERATED {
	no-codingTDD,
	convolutional-coding,
	turbo-coding,
	...
}

TransportFormatSet-CodingRate ::= ENUMERATED {
	half,
	third,
	...
}

TransportFormatSet-CRC-Size ::= ENUMERATED {
	v0,
	v8,
	v12,
	v16,
	v24,
	...
}

TransportFormatSet-ModeDP ::= CHOICE {
	tdd 				TDD-TransportFormatSet-ModeDP,
	notApplicable				NULL,
	...
}

TransportFormatSet-ModeSSP ::= CHOICE {
	tdd				TransportFormatSet-SecondInterleavingMode,
	notApplicable				NULL,
	...
}

TransportFormatSet-NrOfTransportBlocks ::= INTEGER (0..512)

TransportFormatSet-RateMatchingAttribute ::= INTEGER (1..maxRateMatching)

TransportFormatSet-SecondInterleavingMode ::= ENUMERATED {
	frame-related,
	timeSlot-related,
	...
}

TransportFormatSet-TransmissionTimeIntervalDynamic ::= ENUMERATED {
	msec-10,
	msec-20,
	msec-40,
	msec-80,
	...
}

TransportFormatSet-TransmissionTimeIntervalSemiStatic ::= ENUMERATED {
	msec-10,
	msec-20,
	msec-40,
	msec-80,
	dynamic,
	...,
	msec-5
}

TransportFormatSet-TransportBlockSize ::= INTEGER (0..5000)

TransportLayerAddress ::= BIT STRING (SIZE (1..160, ...))

TS0-CapabilityLCR ::= ENUMERATED {
	tS0-Capable,
	tS0-Not-Capable
}

TSTD-Indicator ::= ENUMERATED {
	active,
	inactive
}


TSN-Length ::= ENUMERATED {
	tsn-6bits,
	tsn-9bits
}

TUTRANGANSS ::= SEQUENCE {
	mS				INTEGER(0..16383),
	lS				INTEGER(0..4294967295)
}

TUTRANGANSSAccuracyClass ::= ENUMERATED {
	ganssAccuracy-class-A,
	ganssAccuracy-class-B,
	ganssAccuracy-class-C,
	...
}

TUTRANGANSSMeasurementThresholdInformation ::= SEQUENCE {
	tUTRANGANSSChangeLimit				INTEGER(1..256)												OPTIONAL,
	predictedTUTRANGANSSDeviationLimit	INTEGER(1..256)												OPTIONAL,
	ie-Extensions			ProtocolExtensionContainer { { TUTRANGANSSMeasurementThresholdInformation-ExtIEs } }	OPTIONAL,
	...
}

TUTRANGANSSMeasurementThresholdInformation-ExtIEs NBAP-PROTOCOL-EXTENSION ::= {
	...
}

TUTRANGANSSMeasurementValueInformation ::= SEQUENCE {
	tUTRANGANSS						TUTRANGANSS,
	tUTRANGANSSQuality				INTEGER(0..255)													OPTIONAL,
	tUTRANGANSSDriftRate			INTEGER(-50..50),
	tUTRANGANSSDriftRateQuality		INTEGER(0..50)													OPTIONAL,
	ie-Extensions			ProtocolExtensionContainer { { TUTRANGANSSMeasurementValueInformation-ExtIEs } }	OPTIONAL,
	...
}

TUTRANGANSSMeasurementValueInformation-ExtIEs NBAP-PROTOCOL-EXTENSION ::= {
	{ ID id-GANSS-Time-ID			CRITICALITY ignore		EXTENSION GANSS-Time-ID		PRESENCE 	optional},
	...
}

TUTRANGPS ::= SEQUENCE {
	ms-part 	INTEGER (0..16383),
	ls-part		INTEGER (0..4294967295)
}

TUTRANGPSChangeLimit ::= INTEGER (1..256)
-- Unit chip, Step 1/16 chip, Range 1/16..16 chip

TUTRANGPSDriftRate ::= INTEGER (-50..50)
-- Unit chip/s, Step 1/256 chip/s, Range -50/256..+50/256 chip/s

TUTRANGPSDriftRateQuality ::= INTEGER (0..50)
-- Unit chip/s, Step 1/256 chip/s, Range 0..50/256 chip/s

TUTRANGPSAccuracyClass ::= ENUMERATED {
	accuracy-class-A,
	accuracy-class-B,
	accuracy-class-C,
	...
}

TUTRANGPSMeasurementThresholdInformation ::= SEQUENCE {
	tUTRANGPSChangeLimit					TUTRANGPSChangeLimit					OPTIONAL,
	predictedTUTRANGPSDeviationLimit		PredictedTUTRANGPSDeviationLimit		OPTIONAL,
	iE-Extensions					ProtocolExtensionContainer { { TUTRANGPSMeasurementThresholdInformation-ExtIEs} }		OPTIONAL,
	...
}

TUTRANGPSMeasurementThresholdInformation-ExtIEs NBAP-PROTOCOL-EXTENSION ::= {
	...
}

TUTRANGPSMeasurementValueInformation ::= SEQUENCE {
		tUTRANGPS						TUTRANGPS,
		tUTRANGPSQuality				TUTRANGPSQuality				OPTIONAL,
		tUTRANGPSDriftRate				TUTRANGPSDriftRate,
		tUTRANGPSDriftRateQuality		TUTRANGPSDriftRateQuality		OPTIONAL,
		iE-Extensions					ProtocolExtensionContainer { {TUTRANGPSMeasurementValueInformationItem-ExtIEs} }		OPTIONAL,
		...
}

TUTRANGPSMeasurementValueInformationItem-ExtIEs NBAP-PROTOCOL-EXTENSION ::= {
	...
}

TUTRANGPSQuality ::= INTEGER (0..255)
-- Unit chip, Step 1/16 chip, Range 0.. 255/16 chip

TxDiversityOnDLControlChannelsByMIMOUECapability ::= ENUMERATED {
	dL-Control-Channel-Tx-Diversity-for-MIMO-UE-with-non-diverse-P-CPICH-Capable,
	dL-Control-Channel-Tx-Diversity-for-MIMO-UE-with-non-diverse-P-CPICH-Not-Capable
}

TypeOfError ::= ENUMERATED {
	not-understood,
	missing,
	...
}

-- ==========================================
--	U
-- ==========================================

UARFCN ::= INTEGER (0..16383, ...)
-- corresponds to 0MHz .. 3276.6MHz

UC-Id ::= SEQUENCE {
	rNC-ID				RNC-ID,
	c-ID				C-ID,
	iE-Extensions			ProtocolExtensionContainer { {UC-Id-ExtIEs} } OPTIONAL,
	...
}
UC-Id-ExtIEs NBAP-PROTOCOL-EXTENSION ::= {
	{ ID id-Extended-RNC-ID		CRITICALITY  reject		EXTENSION	Extended-RNC-ID	PRESENCE	optional},
	...
}

UDRE ::= ENUMERATED {
    udre-minusequal-one-m,
    udre-betweenoneandfour-m,
    udre-betweenfourandeight-m,
    udre-greaterequaleight-m
}

UDREGrowthRate ::=					ENUMERATED {
										growth-1-point-5,
										growth-2,
										growth-4,
										growth-6,
										growth-8,
										growth-10,
										growth-12,
										growth-16	}

UDREValidityTime	::=					ENUMERATED {
											val-20sec,
											val-40sec,
											val-80sec,
											val-160sec,
											val-320sec,
											val-640sec,
											val-1280sec,
											val-2560sec	}

UE-AggregateMaximumBitRate ::= SEQUENCE {
	uE-AggregateMaximumBitRateDownlink		UE-AggregateMaximumBitRateDownlink	OPTIONAL,
	uE-AggregateMaximumBitRateUplink		UE-AggregateMaximumBitRateUplink	OPTIONAL,
	...
}

UE-AggregateMaximumBitRateDownlink			::= INTEGER (1..1000000000)
-- Unit is bits per sec

UE-AggregateMaximumBitRateUplink			::= INTEGER (1..1000000000)
-- Unit is bits per sec

UE-AggregateMaximumBitRate-Enforcement-Indicator ::= NULL

UE-Capability-Information ::= SEQUENCE {
	hSDSCH-Physical-Layer-Category		INTEGER (1..64,...),
	iE-Extensions						ProtocolExtensionContainer { { UE-Capability-Information-ExtIEs } }			OPTIONAL,
	...
}

UE-Capability-Information-ExtIEs NBAP-PROTOCOL-EXTENSION ::= {
	{ID id-LCRTDD-uplink-Physical-Channel-Capability	CRITICALITY ignore	EXTENSION LCRTDD-Uplink-Physical-Channel-Capability		PRESENCE optional}|
	{ID id-number-Of-Supported-Carriers					CRITICALITY reject	EXTENSION Number-Of-Supported-Carriers						PRESENCE optional}|
	{ID id-MultiCarrier-HSDSCH-Physical-Layer-Category	CRITICALITY ignore	EXTENSION LCRTDD-HSDSCH-Physical-Layer-Category			PRESENCE optional}|
	{ID id-MIMO-SFMode-Supported-For-HSPDSCHDualStream	CRITICALITY reject	EXTENSION MIMO-SFMode-For-HSPDSCHDualStream				PRESENCE optional}|
	{ID id-UE-TS0-CapabilityLCR							CRITICALITY ignore	EXTENSION UE-TS0-CapabilityLCR									PRESENCE optional},
	...
}

UE-TS0-CapabilityLCR ::= ENUMERATED {
	uE-TS0-Capable,
	uE-TS0-Not-Capable
}

UE-SupportIndicatorExtension ::= BIT STRING (SIZE (32))
-- First bit: Different HS-SCCH In Consecutive TTIs Support Indicator
-- Second bit: HS-SCCH orders in HS-SCCH-less Operation Support Indicator
-- Note that undefined bits are considered as a spare bit and spare bits shall be set to 0 by the transmitter and shall be ignored by the receiver.

LCRTDD-HSDSCH-Physical-Layer-Category ::= INTEGER (1..64)

UE-DPCCH-burst1 ::= ENUMERATED {v1, v2, v5}
	-- Unit subframe

UE-DPCCH-burst2 ::= ENUMERATED {v1, v2, v5}
	-- Unit subframe

UE-DRX-Cycle ::= ENUMERATED {v4, v5, v8, v10, v16, v20}
	-- Unit subframe

UE-DRX-Grant-Monitoring ::= BOOLEAN
	-- true: applied, false: not applied

UE-DTX-Cycle1-2ms ::= ENUMERATED {v1, v4, v5, v8, v10, v16, v20}
	-- Unit subframe

UE-DTX-Cycle1-10ms ::= ENUMERATED {v1, v5, v10, v20}
	-- Unit subframe

UE-DTX-Cycle2-2ms ::= ENUMERATED {v4, v5, v8, v10, v16, v20, v32, v40, v64, v80, v128, v160}
	-- Unit subframe

UE-DTX-Cycle2-10ms ::= ENUMERATED {v5, v10, v20, v40, v80, v160}
	-- Unit subframe

UE-DTX-DRX-Offset ::= INTEGER (0..159)
	-- Unit subframe

UE-DTX-Long-Preamble ::= ENUMERATED {v2, v4, v15}
	-- Units of slots


UL-CapacityCredit ::= INTEGER (0..65535)

UL-Delta-T2TP ::= INTEGER (0..6,...)

UL-DL-mode ::= ENUMERATED {
	ul-only,
	dl-only,
	both-ul-and-dl
}

UL-DPDCH-Indicator-For-E-DCH-Operation ::= ENUMERATED {
	ul-DPDCH-present,
	ul-DPDCH-not-present
}

Uplink-Compressed-Mode-Method 	::= ENUMERATED {
	sFdiv2,
	higher-layer-scheduling,
	...
}

UL-Timeslot-Information ::= SEQUENCE (SIZE (1..maxNrOfULTSs)) OF UL-Timeslot-InformationItem

UL-Timeslot-InformationItem ::= SEQUENCE {
	timeSlot								TimeSlot,
	midambleShiftAndBurstType				MidambleShiftAndBurstType,
	tFCI-Presence							TFCI-Presence,
	uL-Code-InformationList					TDD-UL-Code-Information,
	iE-Extensions							ProtocolExtensionContainer { { UL-Timeslot-InformationItem-ExtIEs} }		OPTIONAL,
	...
}

UL-Timeslot-InformationItem-ExtIEs NBAP-PROTOCOL-EXTENSION ::= {
	...
}

UL-TimeslotLCR-Information ::= SEQUENCE (SIZE (1..maxNrOfULTSLCRs)) OF UL-TimeslotLCR-InformationItem

UL-TimeslotLCR-InformationItem ::= SEQUENCE {
	timeSlotLCR								TimeSlotLCR,
	midambleShiftLCR						MidambleShiftLCR,
	tFCI-Presence							TFCI-Presence,
	uL-Code-InformationList					TDD-UL-Code-LCR-Information,
	iE-Extensions							ProtocolExtensionContainer { { UL-TimeslotLCR-InformationItem-ExtIEs} }		OPTIONAL,
	...
}

UL-TimeslotLCR-InformationItem-ExtIEs NBAP-PROTOCOL-EXTENSION ::= {
{ ID id-PLCCH-Information-UL-TimeslotLCR-Info	CRITICALITY reject		EXTENSION PLCCHinformation	PRESENCE optional },
	...
}

UL-Timeslot768-Information ::= SEQUENCE (SIZE (1..maxNrOfULTSs)) OF UL-Timeslot768-InformationItem

UL-Timeslot768-InformationItem ::= SEQUENCE {
	timeSlot								TimeSlot,
	midambleShiftAndBurstType768			MidambleShiftAndBurstType768,
	tFCI-Presence							TFCI-Presence,
	uL-Code-InformationList					TDD-UL-Code-768-Information,
	iE-Extensions							ProtocolExtensionContainer { { UL-Timeslot768-InformationItem-ExtIEs} }		OPTIONAL,
	...
}

UL-Timeslot768-InformationItem-ExtIEs NBAP-PROTOCOL-EXTENSION ::= {
	...
}

UL-DPCCH-SlotFormat ::= INTEGER (0..5,...)

UL-SIR ::= INTEGER (-82..173)
-- According to mapping in [16]

UL-FP-Mode ::= ENUMERATED {
	normal,
	silent,
	...
}

UL-PhysCH-SF-Variation ::= ENUMERATED {
	sf-variation-supported,
	sf-variation-not-supported
}

UL-ScramblingCode ::= SEQUENCE {
	uL-ScramblingCodeNumber			UL-ScramblingCodeNumber,
	uL-ScramblingCodeLength			UL-ScramblingCodeLength,
	iE-Extensions					ProtocolExtensionContainer { { UL-ScramblingCode-ExtIEs } }		OPTIONAL,
	...
}

UL-ScramblingCode-ExtIEs NBAP-PROTOCOL-EXTENSION ::= {
	...
}

UL-ScramblingCodeNumber ::= INTEGER (0..16777215)

UL-ScramblingCodeLength ::= ENUMERATED {
	short,
	long
}

UL-Synchronisation-Parameters-LCR ::= SEQUENCE {
	uL-Synchronisation-StepSize			UL-Synchronisation-StepSize,
	uL-Synchronisation-Frequency		UL-Synchronisation-Frequency,
	iE-Extensions						ProtocolExtensionContainer { { UL-Synchronisation-Parameters-LCR-ExtIEs } }		OPTIONAL,
	...
}

UL-Synchronisation-Parameters-LCR-ExtIEs NBAP-PROTOCOL-EXTENSION ::= {
	...
}

UL-Synchronisation-StepSize ::= INTEGER (1..8)

UL-Synchronisation-Frequency ::= INTEGER (1..8)

UPPCHPositionLCR ::= INTEGER (0..127)

UL-TimeSlot-ISCP-Info ::= SEQUENCE (SIZE (1..maxNrOfULTSs)) OF	UL-TimeSlot-ISCP-InfoItem

UL-TimeSlot-ISCP-InfoItem ::= SEQUENCE {
 	timeSlot						TimeSlot,
	iSCP							UL-TimeslotISCP-Value,
	iE-Extensions					ProtocolExtensionContainer { { UL-TimeSlot-ISCP-InfoItem-ExtIEs} }		OPTIONAL,
	...
 }

UL-TimeSlot-ISCP-InfoItem-ExtIEs NBAP-PROTOCOL-EXTENSION ::= {
	...
}

UL-TimeSlot-ISCP-LCR-Info ::= SEQUENCE (SIZE (1..maxNrOfULTSLCRs)) OF	UL-TimeSlot-ISCP-LCR-InfoItem

UL-TimeSlot-ISCP-LCR-InfoItem ::= SEQUENCE {
 	timeSlotLCR						TimeSlotLCR,
	iSCP							UL-TimeslotISCP-Value,
	iE-Extensions					ProtocolExtensionContainer { { UL-TimeSlot-ISCP-LCR-InfoItem-ExtIEs} }		OPTIONAL,
	...
 }

UL-TimeSlot-ISCP-LCR-InfoItem-ExtIEs NBAP-PROTOCOL-EXTENSION ::= {
	...
}

UpPTSInterference-For-CellPortion-Value ::= SEQUENCE (SIZE (1..maxNrOfCellPortionsPerCellLCR)) OF UpPTSInterference-For-CellPortion-Value-Item

UpPTSInterference-For-CellPortion-Value-Item ::= SEQUENCE{
	cellPortionLCRID							CellPortionLCRID,
	upPTSInterferenceValue						UpPTSInterferenceValue,
	iE-Extensions							ProtocolExtensionContainer { { UpPTSInterference-For-CellPortion-Value-Item-ExtIEs} }		OPTIONAL,
	...
}

UpPTSInterference-For-CellPortion-Value-Item-ExtIEs NBAP-PROTOCOL-EXTENSION ::= {
	...
}

UpPTSInterferenceValue ::= INTEGER (0..127,...)

Unidirectional-DCH-Indicator	::= ENUMERATED {
	downlink-DCH-only,
	uplink-DCH-only
}

USCH-Information ::= SEQUENCE (SIZE (1..maxNrOfUSCHs)) OF USCH-InformationItem

USCH-InformationItem ::= SEQUENCE {
	uSCH-ID									USCH-ID,
	cCTrCH-ID								CCTrCH-ID,			-- UL CCTrCH in which the USCH is mapped
	transportFormatSet						TransportFormatSet,	-- For USCH
	allocationRetentionPriority				AllocationRetentionPriority,
	iE-Extensions							ProtocolExtensionContainer { { USCH-InformationItem-ExtIEs} }		OPTIONAL,
	...
}

USCH-InformationItem-ExtIEs NBAP-PROTOCOL-EXTENSION ::= {
	{ ID id-bindingID						CRITICALITY	ignore		EXTENSION 	BindingID			PRESENCE 	optional	}|
	-- Shall be ignored if bearer establishment with ALCAP.
	{ ID id-transportlayeraddress			CRITICALITY	ignore		EXTENSION 	TransportLayerAddress	PRESENCE 	optional	}|
	-- Shall be ignored if bearer establishment with ALCAP.
{ ID id-TnlQos							CRITICALITY ignore		EXTENSION	TnlQos	PRESENCE optional	},
	...
}

USCH-InformationResponse ::= SEQUENCE (SIZE (1..maxNrOfUSCHs)) OF USCH-InformationResponseItem

USCH-InformationResponseItem ::= SEQUENCE {
	uSCH-ID										USCH-ID,
	bindingID									BindingID				OPTIONAL,
	transportLayerAddress						TransportLayerAddress	OPTIONAL,
	iE-Extensions								ProtocolExtensionContainer { { USCH-InformationResponseItem-ExtIEs} }		OPTIONAL,
	...
}

USCH-InformationResponseItem-ExtIEs NBAP-PROTOCOL-EXTENSION ::= {
	...
}

UL-TimeslotISCP-For-CellPortion-Value ::= SEQUENCE (SIZE (1..maxNrOfCellPortionsPerCellLCR)) OF UL-TimeslotISCP-For-CellPortion-Value-Item

UL-TimeslotISCP-For-CellPortion-Value-Item ::= SEQUENCE{
	cellPortionLCRID							CellPortionLCRID,
	uL-TimeslotISCP-Value						UL-TimeslotISCP-Value,
	iE-Extensions							ProtocolExtensionContainer { { UL-TimeslotISCP-For-CellPortion-Value-Item-ExtIEs} }		OPTIONAL,
	...
}

UL-TimeslotISCP-For-CellPortion-Value-Item-ExtIEs NBAP-PROTOCOL-EXTENSION ::= {
	...
}

UL-TimeslotISCP-Value ::= INTEGER (0..127)
-- According to mapping in [23]

UL-TimeslotISCP-Value-IncrDecrThres ::= INTEGER (0..126)

USCH-ID ::= INTEGER (0..255)

Uu-ActivationState ::= ENUMERATED {
	activated,
	de-activated,
	...
}

-- ==========================================
--	V
-- ==========================================

-- ==========================================
--	W
-- ==========================================

-- ==========================================
--	X
-- ==========================================

-- ==========================================
--	Y
-- ==========================================

-- ==========================================
--	Z
-- ==========================================

END
