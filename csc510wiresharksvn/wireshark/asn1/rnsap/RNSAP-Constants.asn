-- RNSAP-Constants.asn
--
-- Taken from 3GPP TS 25.423 V9.4.0 (2010-09)
-- http://www.3gpp.org/ftp/Specs/archive/25_series/25.423/25423-790.zip/25423-790.DOC
--
-- 9.3.6	Constant Definitions
--
-- $Id: RNSAP-Constants.asn 52132 2013-09-18 02:48:29Z cmaynard $
--

-- **************************************************************
--
-- Constant definitions
--
-- **************************************************************

RNSAP-Constants {
itu-t (0) identified-organization (4) etsi (0) mobileDomain (0)
umts-Access (20) modules (3) rnsap (1) version1 (1) rnsap-Constants (4) }

DEFINITIONS AUTOMATIC TAGS ::=

BEGIN

IMPORTS
	ProcedureCode,
	ProtocolIE-ID
FROM RNSAP-CommonDataTypes;

-- **************************************************************
--
-- Elementary Procedures
--
-- **************************************************************

id-commonTransportChannelResourcesInitialisation			ProcedureCode ::= 0
id-commonTransportChannelResourcesRelease					ProcedureCode ::= 1
id-compressedModeCommand									ProcedureCode ::= 2
id-downlinkPowerControl										ProcedureCode ::= 3
id-downlinkPowerTimeslotControl								ProcedureCode ::= 4
id-downlinkSignallingTransfer								ProcedureCode ::= 5
id-errorIndication											ProcedureCode ::= 6
id-dedicatedMeasurementFailure								ProcedureCode ::= 7
id-dedicatedMeasurementInitiation							ProcedureCode ::= 8
id-dedicatedMeasurementReporting							ProcedureCode ::= 9
id-dedicatedMeasurementTermination							ProcedureCode ::= 10
id-paging													ProcedureCode ::= 11
id-physicalChannelReconfiguration							ProcedureCode ::= 12
id-privateMessage											ProcedureCode ::= 13
id-radioLinkAddition										ProcedureCode ::= 14
id-radioLinkCongestion										ProcedureCode ::= 34
id-radioLinkDeletion										ProcedureCode ::= 15
id-radioLinkFailure											ProcedureCode ::= 16
id-radioLinkPreemption										ProcedureCode ::= 17
id-radioLinkRestoration										ProcedureCode ::= 18
id-radioLinkSetup											ProcedureCode ::= 19
id-relocationCommit											ProcedureCode ::= 20
id-synchronisedRadioLinkReconfigurationCancellation			ProcedureCode ::= 21
id-synchronisedRadioLinkReconfigurationCommit				ProcedureCode ::= 22
id-synchronisedRadioLinkReconfigurationPreparation			ProcedureCode ::= 23
id-unSynchronisedRadioLinkReconfiguration					ProcedureCode ::= 24
id-uplinkSignallingTransfer									ProcedureCode ::= 25
id-commonMeasurementFailure									ProcedureCode ::= 26
id-commonMeasurementInitiation								ProcedureCode ::= 27
id-commonMeasurementReporting								ProcedureCode ::= 28
id-commonMeasurementTermination								ProcedureCode ::= 29
id-informationExchangeFailure								ProcedureCode ::= 30
id-informationExchangeInitiation							ProcedureCode ::= 31
id-informationReporting										ProcedureCode ::= 32
id-informationExchangeTermination							ProcedureCode ::= 33
id-reset													ProcedureCode ::= 35
id-radioLinkActivation 										ProcedureCode ::= 36
id-gERANuplinkSignallingTransfer							ProcedureCode ::= 37
id-radioLinkParameterUpdate									ProcedureCode ::= 38
id-uEMeasurementFailure										ProcedureCode ::= 39
id-uEMeasurementInitiation									ProcedureCode ::= 40
id-uEMeasurementReporting									ProcedureCode ::= 41
id-uEMeasurementTermination									ProcedureCode ::= 42
id-iurDeactivateTrace										ProcedureCode ::= 43
id-iurInvokeTrace											ProcedureCode ::= 44
id-mBMSAttach												ProcedureCode ::= 45
id-mBMSDetach												ProcedureCode ::= 46
--WS extension
id-Not-used-47												ProcedureCode ::= 47
id-directInformationTransfer								ProcedureCode ::= 48
id-enhancedRelocation										ProcedureCode ::= 49
id-enhancedRelocationCancel									ProcedureCode ::= 50
id-enhancedRelocationSignallingTransfer						ProcedureCode ::= 51
id-enhancedRelocationRelease								ProcedureCode ::= 52
id-mBSFNMCCHInformation										ProcedureCode ::= 53
id-secondaryULFrequencyReporting							ProcedureCode ::= 54
id-secondaryULFrequencyUpdate								ProcedureCode ::= 55

-- **************************************************************
--
-- Lists
--
-- **************************************************************

maxCellSIB11OrSIB12						INTEGER ::= 32
maxCellsMeas							INTEGER ::= 8
maxRateMatching							INTEGER ::= 256
maxNoOfDSCHs							INTEGER ::= 10
maxNoOfDSCHsLCR							INTEGER ::= 10
maxNoOfRB								INTEGER ::= 32
maxNoOfUSCHs							INTEGER ::= 10
maxNoOfUSCHsLCR							INTEGER ::= 10
maxNrOfTFCs								INTEGER ::= 1024
maxNrOfTFs								INTEGER ::= 32
maxNrOfCCTrCHs							INTEGER ::= 16
maxNrOfCCTrCHsLCR						INTEGER ::= 16
maxNrOfDCHs								INTEGER ::= 128
maxNrOfDL-Codes							INTEGER ::= 8
maxNrOfDPCHs							INTEGER ::= 240
maxNrOfDPCHsPerRL-1						INTEGER ::= 239 -- maxNrofCCTrCH*maxNrOfULTs-1
maxNrOfDPCHsLCR							INTEGER ::= 240
maxNrOfDPCHsLCRPerRL-1					INTEGER ::= 95  -- maxNrofCCTrCH*maxNrOfULTsLCR-1
maxNrOfDPCHs768							INTEGER ::= 480
maxNrOfDPCHs768PerRL-1					INTEGER ::= 479
maxNrOfErrors							INTEGER ::= 256
maxNrOfMACcshSDU-Length					INTEGER ::= 16
maxNrOfMBMSServices						INTEGER ::= 128
maxNrOfActiveMBMSServices				INTEGER ::= 256
maxNrOfPoints							INTEGER ::= 15
maxNrOfRLs								INTEGER ::= 16
maxNrOfRLSets							INTEGER ::= maxNrOfRLs
maxNrOfRLSets-1						INTEGER ::= 15	-- maxNrOfRLSets - 1
maxNrOfRLs-1							INTEGER ::= 15	-- maxNrOfRLs - 1
maxNrOfRLs-2							INTEGER ::= 14	-- maxNrOfRLs - 2
maxNrOfUEs								INTEGER ::= 4096
maxNrOfULTs								INTEGER ::= 15
maxNrOfULTsLCR							INTEGER ::= 6
maxNrOfDLTs								INTEGER ::= 15
maxNrOfDLTsLCR							INTEGER ::= 6
maxRNCinURA-1							INTEGER ::= 15
maxTTI-Count							INTEGER ::= 4
maxCTFC									INTEGER ::= 16777215
maxNrOfNeighbouringRNCs					INTEGER ::= 10
maxNrOfFDDNeighboursPerRNC				INTEGER ::= 256
maxNrOfGSMNeighboursPerRNC				INTEGER ::= 256
maxNrOfTDDNeighboursPerRNC				INTEGER ::= 256
maxNrOfFACHs							INTEGER	::=	8
maxNrOfLCRTDDNeighboursPerRNC			INTEGER ::= 256
maxIBSEG								INTEGER ::= 16
maxNrOfSCCPCHs							INTEGER	::=	8
maxNrOfSCCPCHs768						INTEGER	::=	16
maxTGPS									INTEGER ::= 6
maxNrOfTS								INTEGER ::= 15
maxNrOfLevels							INTEGER ::= 256
maxNrOfTsLCR							INTEGER ::= 6
maxNoSat								INTEGER ::= 16
maxNoGPSTypes							INTEGER ::= 8
maxNrOfMeasNCell						INTEGER ::= 96
maxNrOfMeasNCell-1						INTEGER ::= 95	-- maxNrOfMeasNCell - 1
maxResetContext							INTEGER ::= 250
maxResetContextGroup					INTEGER ::= 32
maxNrOfHARQProc							INTEGER ::= 8
maxNrOfHSSCCHCodes						INTEGER ::= 4
maxNrOfHSSICHs							INTEGER ::= 4
maxNrOfHSSICHs-1						INTEGER ::= 3
maxNrOfMACdFlows						INTEGER ::= 8
maxNrOfMACdFlows-1						INTEGER ::= 7	-- maxNrOfMACdFlows - 1
maxNrOfMACdPDUSize						INTEGER ::= 32
maxNrOfPDUIndexes						INTEGER ::= 8
maxNrOfPDUIndexes-1						INTEGER ::= 7	-- maxNrOfPDUIndexes - 1
maxNrOfPrioQueues						INTEGER ::= 8
maxNrOfPrioQueues-1						INTEGER ::= 7	-- maxNrOfPrioQueues - 1
maxNrOfSNAs								INTEGER ::= 65536
maxNrOfSatAlmanac-maxNoSat				INTEGER ::= 16
maxNrOfGERANSI 							INTEGER ::= 8
maxNrOfInterfaces						INTEGER ::= 16
maxNrofSigSeqERGHICH-1					INTEGER ::= 39
maxNrOfCells							INTEGER ::= 65536
maxNrOfAddFreq							INTEGER ::= 8
maxNrOfCellsPerFreq						INTEGER ::= 65536
maxNrOfEDCHMACdFlows-1					INTEGER ::= 7
maxNrOfEDCH-HARQ-PO-QUANTSTEPs			INTEGER ::= 6
maxNrOfEDPCCH-PO-QUANTSTEPs				INTEGER ::= 8
maxNrOfEDCHHARQProcesses2msEDCH			INTEGER ::= 8
maxNrOfBits-MACe-PDU-non-scheduled		INTEGER ::= 19982
maxNrOfRefETFCIs						INTEGER ::= 8
maxNrOfRefETFCI-PO-QUANTSTEPs			INTEGER ::= 29
maxNrOfEDCHMACdFlows					INTEGER ::= 8
maxNoOfLogicalChannels					INTEGER ::= 16 -- only maximum 15 can be used
maxNrOfRefBetas							INTEGER ::= 8
maxNrOfEAGCHCodes						INTEGER ::= 4
maxNrOfHS-DSCHTBSs						INTEGER ::= 90
maxNrOfHS-DSCHTBSs-HS-SCCHless			INTEGER ::= 4
maxHS-PDSCHCodeNrComp-1					INTEGER ::= 15
maxNrOfEHICHCodes						INTEGER ::= 4
maxGANSSSat								INTEGER ::= 64
maxNoGANSS								INTEGER ::= 8
maxSgnType								INTEGER ::= 8
maxNrOfBroadcastPLMNs					INTEGER ::= 5
maxHSDPAFrequency						INTEGER ::= 8
maxHSDPAFrequency-1						INTEGER ::= 7
maxFrequencyinCell						INTEGER ::= 12
maxFrequencyinCell-1					INTEGER ::= 11
maxGANSSSatAlmanac						INTEGER ::= 36
maxGANSSClockMod						INTEGER ::= 4
maxNrOfEDCHRLs							INTEGER ::= 4
maxEARFCN								INTEGER ::= 65535
maxNrOfEUTRANeighboursPerRNC			INTEGER ::= 256
maxNrOfMCCHMessages						INTEGER ::= 5
maxNrOfMBMSL3							INTEGER ::= 64
maxNrOfEDCHMACdFlowsLCR					INTEGER ::= 256
maxNrOfEDCHMACdFlowsLCR-1				INTEGER ::= 255
maxNrOfPreconfiguredNeighbours			INTEGER ::= 256
maxNrOfHSDSCH-1							INTEGER ::= 32
maxNrOfHSDSCH							INTEGER ::= 33
maxGANSS-1								INTEGER ::= 7
maxlengthMBMSconcatservlists			INTEGER ::= 96
maxNoOfTBSs-Mapping-HS-DSCH-SPS			INTEGER ::= 4
maxNoOfTBSs-Mapping-HS-DSCH-SPS-1		INTEGER ::= 3
maxNoOfHS-DSCH-TBSsLCR					INTEGER ::= 64
maxNoOfRepetition-Period-LCR			INTEGER ::= 4
maxNoOfRepetitionPeriod-SPS-LCR-1		INTEGER ::= 3
maxNoOf-HS-SICH-SPS						INTEGER ::= 4
maxNoOf-HS-SICH-SPS-1					INTEGER ::= 3
maxNoOfNon-HS-SCCH-Assosiated-HS-SICH	INTEGER ::= 4
maxNrOfEDCH-1							INTEGER ::= 32
maxNrOfDCHMeasurementOccasionPatternSequence	INTEGER ::= 6



-- **************************************************************
--
-- IEs
--
-- **************************************************************

id-AllowedQueuingTime														ProtocolIE-ID ::= 4
id-Allowed-Rate-Information													ProtocolIE-ID ::= 42
id-AntennaColocationIndicator												ProtocolIE-ID ::= 309
id-BindingID																ProtocolIE-ID ::= 5
id-C-ID																		ProtocolIE-ID ::= 6
id-C-RNTI																	ProtocolIE-ID ::= 7
id-Cell-Capacity-Class-Value												ProtocolIE-ID ::= 303
id-CFN																		ProtocolIE-ID ::= 8
id-CN-CS-DomainIdentifier													ProtocolIE-ID ::= 9
id-CN-PS-DomainIdentifier													ProtocolIE-ID ::= 10
id-Cause																	ProtocolIE-ID ::= 11
id-CoverageIndicator														ProtocolIE-ID ::= 310
id-CriticalityDiagnostics													ProtocolIE-ID ::= 20
id-ContextInfoItem-Reset													ProtocolIE-ID ::= 211
id-ContextGroupInfoItem-Reset												ProtocolIE-ID ::= 515
id-D-RNTI																	ProtocolIE-ID ::= 21
id-D-RNTI-ReleaseIndication													ProtocolIE-ID ::= 22
id-DCHs-to-Add-FDD															ProtocolIE-ID ::= 26
id-DCHs-to-Add-TDD															ProtocolIE-ID ::= 27
id-DCH-DeleteList-RL-ReconfPrepFDD											ProtocolIE-ID ::= 30
id-DCH-DeleteList-RL-ReconfPrepTDD											ProtocolIE-ID ::= 31
id-DCH-DeleteList-RL-ReconfRqstFDD											ProtocolIE-ID ::= 32
id-DCH-DeleteList-RL-ReconfRqstTDD											ProtocolIE-ID ::= 33
id-DCH-FDD-Information														ProtocolIE-ID ::= 34
id-DCH-TDD-Information														ProtocolIE-ID ::= 35
id-FDD-DCHs-to-Modify														ProtocolIE-ID ::= 39
id-TDD-DCHs-to-Modify														ProtocolIE-ID ::= 40
id-DCH-InformationResponse													ProtocolIE-ID ::= 43
id-DCH-Rate-InformationItem-RL-CongestInd									ProtocolIE-ID ::= 38
id-DL-CCTrCH-InformationAddItem-RL-ReconfPrepTDD							ProtocolIE-ID ::= 44
id-DL-CCTrCH-InformationListIE-RL-ReconfReadyTDD							ProtocolIE-ID ::= 45
id-DL-CCTrCH-InformationDeleteItem-RL-ReconfRqstTDD							ProtocolIE-ID ::= 46
id-DL-CCTrCH-InformationItem-RL-SetupRqstTDD								ProtocolIE-ID ::= 47
id-DL-CCTrCH-InformationListIE-PhyChReconfRqstTDD							ProtocolIE-ID ::= 48
id-DL-CCTrCH-InformationListIE-RL-AdditionRspTDD							ProtocolIE-ID ::= 49
id-DL-CCTrCH-InformationListIE-RL-SetupRspTDD								ProtocolIE-ID ::= 50
id-DL-CCTrCH-InformationAddList-RL-ReconfPrepTDD							ProtocolIE-ID ::= 51
id-DL-CCTrCH-InformationDeleteList-RL-ReconfRqstTDD							ProtocolIE-ID ::= 52
id-DL-CCTrCH-InformationList-RL-SetupRqstTDD								ProtocolIE-ID ::= 53
id-FDD-DL-CodeInformation													ProtocolIE-ID ::= 54
id-DL-DPCH-Information-RL-ReconfPrepFDD										ProtocolIE-ID ::= 59
id-DL-DPCH-Information-RL-SetupRqstFDD										ProtocolIE-ID ::= 60
id-DL-DPCH-Information-RL-ReconfRqstFDD										ProtocolIE-ID ::= 61
id-DL-DPCH-InformationItem-PhyChReconfRqstTDD								ProtocolIE-ID ::= 62
id-DL-DPCH-InformationItem-RL-AdditionRspTDD								ProtocolIE-ID ::= 63
id-DL-DPCH-InformationItem-RL-SetupRspTDD									ProtocolIE-ID ::= 64
id-DL-DPCH-TimingAdjustment													ProtocolIE-ID ::= 278
id-DLReferencePower															ProtocolIE-ID ::= 67
id-DLReferencePowerList-DL-PC-Rqst											ProtocolIE-ID ::= 68
id-DL-ReferencePowerInformation-DL-PC-Rqst									ProtocolIE-ID ::= 69
id-DPC-Mode																	ProtocolIE-ID ::= 12
id-DRXCycleLengthCoefficient												ProtocolIE-ID ::= 70
id-DedicatedMeasurementObjectType-DM-Fail-Ind								ProtocolIE-ID ::= 470
id-DedicatedMeasurementObjectType-DM-Fail									ProtocolIE-ID ::= 471
id-DedicatedMeasurementObjectType-DM-Rprt									ProtocolIE-ID ::= 71
id-DedicatedMeasurementObjectType-DM-Rqst									ProtocolIE-ID ::= 72
id-DedicatedMeasurementObjectType-DM-Rsp									ProtocolIE-ID ::= 73
id-DedicatedMeasurementType													ProtocolIE-ID ::= 74
id-FACH-InfoForUESelectedS-CCPCH-CTCH-ResourceRspFDD						ProtocolIE-ID ::= 82
id-FACH-InfoForUESelectedS-CCPCH-CTCH-ResourceRspTDD						ProtocolIE-ID ::= 83
id-Guaranteed-Rate-Information												ProtocolIE-ID ::= 41
id-IMSI																		ProtocolIE-ID ::= 84
id-HCS-Prio																	ProtocolIE-ID ::= 311
id-L3-Information															ProtocolIE-ID ::= 85
id-AdjustmentPeriod															ProtocolIE-ID ::= 90
id-MaxAdjustmentStep														ProtocolIE-ID ::= 91
id-MeasurementFilterCoefficient												ProtocolIE-ID ::= 92
id-MessageStructure															ProtocolIE-ID ::= 57
id-MeasurementID															ProtocolIE-ID ::= 93
id-Neighbouring-GSM-CellInformation											ProtocolIE-ID ::= 13
id-Neighbouring-UMTS-CellInformationItem									ProtocolIE-ID ::= 95
--WS extension
id-Unknown-305																ProtocolIE-ID ::= 304
id-NRT-Load-Information-Value												ProtocolIE-ID ::= 305
id-NRT-Load-Information-Value-IncrDecrThres									ProtocolIE-ID ::= 306
id-PagingArea-PagingRqst													ProtocolIE-ID ::= 102
id-FACH-FlowControlInformation												ProtocolIE-ID ::= 103
id-PartialReportingIndicator												ProtocolIE-ID ::= 472
id-Permanent-NAS-UE-Identity												ProtocolIE-ID ::= 17
id-PowerAdjustmentType														ProtocolIE-ID ::= 107
--WS extension
id-Unknown-108																ProtocolIE-ID ::= 108
id-RANAP-RelocationInformation												ProtocolIE-ID ::= 109
id-RL-Information-PhyChReconfRqstFDD										ProtocolIE-ID ::= 110
id-RL-Information-PhyChReconfRqstTDD										ProtocolIE-ID ::= 111
id-RL-Information-RL-AdditionRqstFDD										ProtocolIE-ID ::= 112
id-RL-Information-RL-AdditionRqstTDD										ProtocolIE-ID ::= 113
id-RL-Information-RL-DeletionRqst											ProtocolIE-ID ::= 114
id-RL-Information-RL-FailureInd												ProtocolIE-ID ::= 115
id-RL-Information-RL-ReconfPrepFDD											ProtocolIE-ID ::= 116
id-RL-Information-RL-RestoreInd												ProtocolIE-ID ::= 117
id-RL-Information-RL-SetupRqstFDD											ProtocolIE-ID ::= 118
id-RL-Information-RL-SetupRqstTDD											ProtocolIE-ID ::= 119
id-RL-InformationItem-RL-CongestInd											ProtocolIE-ID ::= 55
id-RL-InformationItem-DM-Rprt												ProtocolIE-ID ::= 120
id-RL-InformationItem-DM-Rqst												ProtocolIE-ID ::= 121
id-RL-InformationItem-DM-Rsp												ProtocolIE-ID ::= 122
id-RL-InformationItem-RL-PreemptRequiredInd									ProtocolIE-ID ::= 2
id-RL-InformationItem-RL-SetupRqstFDD										ProtocolIE-ID ::= 123
id-RL-InformationList-RL-CongestInd											ProtocolIE-ID ::= 56
id-RL-InformationList-RL-AdditionRqstFDD									ProtocolIE-ID ::= 124
id-RL-InformationList-RL-DeletionRqst										ProtocolIE-ID ::= 125
id-RL-InformationList-RL-PreemptRequiredInd									ProtocolIE-ID ::= 1
id-RL-InformationList-RL-ReconfPrepFDD										ProtocolIE-ID ::= 126
id-RL-InformationResponse-RL-AdditionRspTDD									ProtocolIE-ID ::= 127
id-RL-InformationResponse-RL-ReconfReadyTDD									ProtocolIE-ID ::= 128
id-RL-InformationResponse-RL-SetupRspTDD									ProtocolIE-ID ::= 129
id-RL-InformationResponseItem-RL-AdditionRspFDD								ProtocolIE-ID ::= 130
id-RL-InformationResponseItem-RL-ReconfReadyFDD								ProtocolIE-ID ::= 131
id-RL-InformationResponseItem-RL-ReconfRspFDD								ProtocolIE-ID ::= 132
id-RL-InformationResponseItem-RL-SetupRspFDD								ProtocolIE-ID ::= 133
id-RL-InformationResponseList-RL-AdditionRspFDD								ProtocolIE-ID ::= 134
id-RL-InformationResponseList-RL-ReconfReadyFDD								ProtocolIE-ID ::= 135
id-RL-InformationResponseList-RL-ReconfRspFDD								ProtocolIE-ID ::= 136
id-RL-InformationResponse-RL-ReconfRspTDD									ProtocolIE-ID ::= 28
id-RL-InformationResponseList-RL-SetupRspFDD								ProtocolIE-ID ::= 137
id-RL-ReconfigurationFailure-RL-ReconfFail									ProtocolIE-ID ::= 141
id-RL-Set-InformationItem-DM-Rprt											ProtocolIE-ID ::= 143
id-RL-Set-InformationItem-DM-Rqst											ProtocolIE-ID ::= 144
id-RL-Set-InformationItem-DM-Rsp											ProtocolIE-ID ::= 145
id-RL-Set-Information-RL-FailureInd											ProtocolIE-ID ::= 146
id-RL-Set-Information-RL-RestoreInd											ProtocolIE-ID ::= 147
id-RL-Set-Successful-InformationItem-DM-Fail								ProtocolIE-ID ::= 473
id-RL-Set-Unsuccessful-InformationItem-DM-Fail								ProtocolIE-ID ::= 474
id-RL-Set-Unsuccessful-InformationItem-DM-Fail-Ind							ProtocolIE-ID ::= 475
id-RL-Successful-InformationItem-DM-Fail									ProtocolIE-ID ::= 476
id-RL-Unsuccessful-InformationItem-DM-Fail									ProtocolIE-ID ::= 477
id-RL-Unsuccessful-InformationItem-DM-Fail-Ind								ProtocolIE-ID ::= 478
id-ReportCharacteristics													ProtocolIE-ID ::= 152
id-Reporting-Object-RL-FailureInd											ProtocolIE-ID ::= 153
id-Reporing-Object-RL-RestoreInd											ProtocolIE-ID ::= 154
id-RT-Load-Value															ProtocolIE-ID ::= 307
id-RT-Load-Value-IncrDecrThres												ProtocolIE-ID ::= 308
id-S-RNTI																	ProtocolIE-ID ::= 155
id-ResetIndicator															ProtocolIE-ID ::= 244
id-RNC-ID																	ProtocolIE-ID ::= 245
id-SAI																		ProtocolIE-ID ::= 156
id-SRNC-ID																	ProtocolIE-ID ::= 157
id-SuccessfulRL-InformationResponse-RL-AdditionFailureFDD					ProtocolIE-ID ::= 159
id-SuccessfulRL-InformationResponse-RL-SetupFailureFDD						ProtocolIE-ID ::= 160
--WS extension
id-Unknown-161																ProtocolIE-ID ::= 161
id-Unknown-162																ProtocolIE-ID ::= 162
id-TransportBearerID														ProtocolIE-ID ::= 163
id-TransportBearerRequestIndicator											ProtocolIE-ID ::= 164
id-TransportLayerAddress													ProtocolIE-ID ::= 165
id-TypeOfError																ProtocolIE-ID ::= 140
id-UC-ID																	ProtocolIE-ID ::= 166
id-UL-CCTrCH-AddInformation-RL-ReconfPrepTDD								ProtocolIE-ID ::= 167
id-Unknown-168																ProtocolIE-ID ::= 168
id-UL-CCTrCH-InformationAddList-RL-ReconfPrepTDD							ProtocolIE-ID ::= 169
id-Unknown-170																ProtocolIE-ID ::= 170
id-UL-CCTrCH-InformationItem-RL-SetupRqstTDD								ProtocolIE-ID ::= 171
id-UL-CCTrCH-InformationList-RL-SetupRqstTDD								ProtocolIE-ID ::= 172
id-UL-CCTrCH-InformationListIE-PhyChReconfRqstTDD							ProtocolIE-ID ::= 173
id-UL-CCTrCH-InformationListIE-RL-AdditionRspTDD							ProtocolIE-ID ::= 174
id-UL-CCTrCH-InformationListIE-RL-ReconfReadyTDD							ProtocolIE-ID ::= 175
id-UL-CCTrCH-InformationListIE-RL-SetupRspTDD								ProtocolIE-ID ::= 176
id-UL-DPCH-Information-RL-ReconfPrepFDD										ProtocolIE-ID ::= 177
id-UL-DPCH-Information-RL-ReconfRqstFDD										ProtocolIE-ID ::= 178
id-UL-DPCH-Information-RL-SetupRqstFDD										ProtocolIE-ID ::= 179
id-UL-DPCH-InformationItem-PhyChReconfRqstTDD								ProtocolIE-ID ::= 180
id-UL-DPCH-InformationItem-RL-AdditionRspTDD								ProtocolIE-ID ::= 181
id-UL-DPCH-InformationItem-RL-SetupRspTDD									ProtocolIE-ID ::= 182
id-UL-DPCH-InformationAddListIE-RL-ReconfReadyTDD							ProtocolIE-ID ::= 183
id-UL-SIRTarget																ProtocolIE-ID ::= 184
id-URA-Information															ProtocolIE-ID ::= 185
--WS extension
id-Unknown-186																ProtocolIE-ID ::= 186
id-Unknown-187																ProtocolIE-ID ::= 187
id-UnsuccessfulRL-InformationResponse-RL-AdditionFailureFDD					ProtocolIE-ID ::= 188
id-UnsuccessfulRL-InformationResponse-RL-SetupFailureFDD					ProtocolIE-ID ::= 189
id-UnsuccessfulRL-InformationResponse-RL-SetupFailureTDD					ProtocolIE-ID ::= 190
--WS extension
id-Unknown-191																ProtocolIE-ID ::= 191
id-Unknown-192																ProtocolIE-ID ::= 192
id-Active-Pattern-Sequence-Information										ProtocolIE-ID ::= 193
id-AdjustmentRatio															ProtocolIE-ID ::= 194
--WS extension
id-Unknown-195																ProtocolIE-ID ::= 195
id-Unknown-196																ProtocolIE-ID ::= 196
id-CauseLevel-RL-AdditionFailureFDD											ProtocolIE-ID ::= 197
id-CauseLevel-RL-AdditionFailureTDD											ProtocolIE-ID ::= 198
id-CauseLevel-RL-ReconfFailure												ProtocolIE-ID ::= 199
id-CauseLevel-RL-SetupFailureFDD											ProtocolIE-ID ::= 200
id-CauseLevel-RL-SetupFailureTDD											ProtocolIE-ID ::= 201
id-DL-CCTrCH-InformationDeleteItem-RL-ReconfPrepTDD							ProtocolIE-ID ::= 205
id-DL-CCTrCH-InformationModifyItem-RL-ReconfPrepTDD							ProtocolIE-ID ::= 206
id-DL-CCTrCH-InformationModifyItem-RL-ReconfRqstTDD							ProtocolIE-ID ::= 207
id-DL-CCTrCH-InformationDeleteList-RL-ReconfPrepTDD							ProtocolIE-ID ::= 208
id-DL-CCTrCH-InformationModifyList-RL-ReconfPrepTDD							ProtocolIE-ID ::= 209
id-DL-CCTrCH-InformationModifyList-RL-ReconfRqstTDD							ProtocolIE-ID ::= 210
id-DL-DPCH-InformationAddListIE-RL-ReconfReadyTDD							ProtocolIE-ID ::= 212
id-DL-DPCH-InformationDeleteListIE-RL-ReconfReadyTDD						ProtocolIE-ID ::= 213
id-DL-DPCH-InformationModifyListIE-RL-ReconfReadyTDD						ProtocolIE-ID ::= 214
id-DSCHs-to-Add-TDD															ProtocolIE-ID ::= 215
id-Unused-ProtocolIE-ID-216													ProtocolIE-ID ::= 216
id-DSCH-DeleteList-RL-ReconfPrepTDD											ProtocolIE-ID ::= 217
id-Unused-ProtocolIE-ID-218													ProtocolIE-ID ::= 218
id-Unused-ProtocolIE-ID-219													ProtocolIE-ID ::= 219
id-DSCH-InformationListIE-RL-AdditionRspTDD									ProtocolIE-ID ::= 220
id-DSCH-InformationListIEs-RL-SetupRspTDD									ProtocolIE-ID ::= 221
id-DSCH-TDD-Information														ProtocolIE-ID ::= 222
id-Unused-ProtocolIE-ID-223													ProtocolIE-ID ::= 223
id-Unused-ProtocolIE-ID-226													ProtocolIE-ID ::= 226
id-DSCH-ModifyList-RL-ReconfPrepTDD											ProtocolIE-ID ::= 227
id-Unused-ProtocolIE-ID-228													ProtocolIE-ID ::= 228
id-Unused-ProtocolIE-ID-324													ProtocolIE-ID ::= 324
id-Unused-ProtocolIE-ID-229													ProtocolIE-ID ::= 229
id-DSCHToBeAddedOrModifiedList-RL-ReconfReadyTDD							ProtocolIE-ID ::= 230
--WS extension
id-Unknown-231																ProtocolIE-ID ::= 231
id-Unused-ProtocolIE-ID-29													ProtocolIE-ID ::= 29
id-Unused-ProtocolIE-ID-225													ProtocolIE-ID ::= 225
id-GA-Cell																	ProtocolIE-ID ::= 232
id-GA-CellAdditionalShapes													ProtocolIE-ID ::= 3
id-Unused-ProtocolIE-ID-246													ProtocolIE-ID ::= 246
--WS extension
id-Unknown-254																ProtocolIE-ID ::= 254
id-Transmission-Gap-Pattern-Sequence-Information							ProtocolIE-ID ::= 255
id-UL-CCTrCH-DeleteInformation-RL-ReconfPrepTDD								ProtocolIE-ID ::= 256
id-UL-CCTrCH-ModifyInformation-RL-ReconfPrepTDD								ProtocolIE-ID ::= 257
id-UL-CCTrCH-InformationModifyItem-RL-ReconfRqstTDD							ProtocolIE-ID ::= 258
id-UL-CCTrCH-InformationDeleteList-RL-ReconfPrepTDD							ProtocolIE-ID ::= 259
id-UL-CCTrCH-InformationModifyList-RL-ReconfPrepTDD							ProtocolIE-ID ::= 260
id-UL-CCTrCH-InformationModifyList-RL-ReconfRqstTDD							ProtocolIE-ID ::= 261
id-UL-CCTrCH-InformationDeleteItem-RL-ReconfRqstTDD							ProtocolIE-ID ::= 262
id-UL-CCTrCH-InformationDeleteList-RL-ReconfRqstTDD							ProtocolIE-ID ::= 263
id-UL-DPCH-InformationDeleteListIE-RL-ReconfReadyTDD						ProtocolIE-ID ::= 264
id-UL-DPCH-InformationModifyListIE-RL-ReconfReadyTDD						ProtocolIE-ID ::= 265
id-UnsuccessfulRL-InformationResponse-RL-AdditionFailureTDD					ProtocolIE-ID ::= 266
id-USCHs-to-Add																ProtocolIE-ID ::= 267
id-USCH-DeleteList-RL-ReconfPrepTDD											ProtocolIE-ID ::= 268
id-USCH-InformationListIE-RL-AdditionRspTDD									ProtocolIE-ID ::= 269
id-USCH-InformationListIEs-RL-SetupRspTDD									ProtocolIE-ID ::= 270
id-USCH-Information															ProtocolIE-ID ::= 271
id-USCH-ModifyList-RL-ReconfPrepTDD											ProtocolIE-ID ::= 272
id-USCHToBeAddedOrModifiedList-RL-ReconfReadyTDD							ProtocolIE-ID ::= 273
id-DL-Physical-Channel-Information-RL-SetupRqstTDD							ProtocolIE-ID ::= 274
id-UL-Physical-Channel-Information-RL-SetupRqstTDD							ProtocolIE-ID ::= 275
id-ClosedLoopMode1-SupportIndicator											ProtocolIE-ID ::= 276
id-Unused-ProtocolIE-ID-277													ProtocolIE-ID ::= 277
id-STTD-SupportIndicator													ProtocolIE-ID ::= 279
id-CFNReportingIndicator             										ProtocolIE-ID ::= 14
id-CNOriginatedPage-PagingRqst												ProtocolIE-ID ::= 23
id-InnerLoopDLPCStatus														ProtocolIE-ID ::= 24
id-PropagationDelay															ProtocolIE-ID ::= 25
id-RxTimingDeviationForTA													ProtocolIE-ID ::= 36
id-timeSlot-ISCP															ProtocolIE-ID ::= 37
id-CCTrCH-InformationItem-RL-FailureInd										ProtocolIE-ID ::= 15
id-CCTrCH-InformationItem-RL-RestoreInd										ProtocolIE-ID ::= 16
id-CommonMeasurementAccuracy												ProtocolIE-ID ::= 280
id-CommonMeasurementObjectType-CM-Rprt										ProtocolIE-ID ::= 281
id-CommonMeasurementObjectType-CM-Rqst										ProtocolIE-ID ::= 282
id-CommonMeasurementObjectType-CM-Rsp										ProtocolIE-ID ::= 283
id-CommonMeasurementType													ProtocolIE-ID ::= 284
id-CongestionCause 															ProtocolIE-ID ::= 18
id-SFN																		ProtocolIE-ID ::= 285
id-SFNReportingIndicator													ProtocolIE-ID ::= 286
id-InformationExchangeID													ProtocolIE-ID ::= 287
id-InformationExchangeObjectType-InfEx-Rprt									ProtocolIE-ID ::= 288
id-InformationExchangeObjectType-InfEx-Rqst									ProtocolIE-ID ::= 289
id-InformationExchangeObjectType-InfEx-Rsp									ProtocolIE-ID ::= 290
id-InformationReportCharacteristics											ProtocolIE-ID ::= 291
id-InformationType															ProtocolIE-ID ::= 292
id-neighbouring-LCR-TDD-CellInformation										ProtocolIE-ID ::= 58
id-DL-Timeslot-ISCP-LCR-Information-RL-SetupRqstTDD							ProtocolIE-ID ::= 65
id-RL-LCR-InformationResponse-RL-SetupRspTDD								ProtocolIE-ID ::= 66
id-UL-CCTrCH-LCR-InformationListIE-RL-SetupRspTDD							ProtocolIE-ID ::= 75
id-UL-DPCH-LCR-InformationItem-RL-SetupRspTDD								ProtocolIE-ID ::= 76
id-DL-CCTrCH-LCR-InformationListIE-RL-SetupRspTDD							ProtocolIE-ID ::= 77
id-DL-DPCH-LCR-InformationItem-RL-SetupRspTDD								ProtocolIE-ID ::= 78
id-DSCH-LCR-InformationListIEs-RL-SetupRspTDD								ProtocolIE-ID ::= 79
id-USCH-LCR-InformationListIEs-RL-SetupRspTDD								ProtocolIE-ID ::= 80
id-DL-Timeslot-ISCP-LCR-Information-RL-AdditionRqstTDD						ProtocolIE-ID ::= 81
id-RL-LCR-InformationResponse-RL-AdditionRspTDD								ProtocolIE-ID ::= 86
id-UL-CCTrCH-LCR-InformationListIE-RL-AdditionRspTDD						ProtocolIE-ID ::= 87
id-UL-DPCH-LCR-InformationItem-RL-AdditionRspTDD							ProtocolIE-ID ::= 88
id-DL-CCTrCH-LCR-InformationListIE-RL-AdditionRspTDD						ProtocolIE-ID ::= 89
id-DL-DPCH-LCR-InformationItem-RL-AdditionRspTDD							ProtocolIE-ID ::= 94
id-DSCH-LCR-InformationListIEs-RL-AdditionRspTDD							ProtocolIE-ID ::= 96
id-USCH-LCR-InformationListIEs-RL-AdditionRspTDD							ProtocolIE-ID ::= 97
id-UL-DPCH-LCR-InformationAddListIE-RL-ReconfReadyTDD						ProtocolIE-ID ::= 98
--WS extension
id-Unknown-99																ProtocolIE-ID ::= 99
id-UL-Timeslot-LCR-InformationModifyList-RL-ReconfReadyTDD					ProtocolIE-ID ::= 100
id-DL-DPCH-LCR-InformationAddListIE-RL-ReconfReadyTDD						ProtocolIE-ID ::= 101
id-DL-Timeslot-LCR-InformationModifyList-RL-ReconfReadyTDD					ProtocolIE-ID ::= 104
id-UL-Timeslot-LCR-InformationList-PhyChReconfRqstTDD						ProtocolIE-ID ::= 105
id-DL-Timeslot-LCR-InformationList-PhyChReconfRqstTDD						ProtocolIE-ID ::= 106
id-timeSlot-ISCP-LCR-List-DL-PC-Rqst-TDD									ProtocolIE-ID ::= 138
id-TSTD-Support-Indicator-RL-SetupRqstTDD									ProtocolIE-ID ::= 139
id-RestrictionStateIndicator												ProtocolIE-ID ::= 142
id-Load-Value																ProtocolIE-ID ::= 233
id-Load-Value-IncrDecrThres													ProtocolIE-ID ::= 234
id-OnModification															ProtocolIE-ID ::= 235
id-Received-Total-Wideband-Power-Value										ProtocolIE-ID ::= 236
id-Received-Total-Wideband-Power-Value-IncrDecrThres						ProtocolIE-ID ::= 237
id-SFNSFNMeasurementThresholdInformation									ProtocolIE-ID ::= 238
id-Transmitted-Carrier-Power-Value											ProtocolIE-ID ::= 239
id-Transmitted-Carrier-Power-Value-IncrDecrThres							ProtocolIE-ID ::= 240
id-TUTRANGPSMeasurementThresholdInformation									ProtocolIE-ID ::= 241
id-UL-Timeslot-ISCP-Value													ProtocolIE-ID ::= 242
id-UL-Timeslot-ISCP-Value-IncrDecrThres										ProtocolIE-ID ::= 243
id-Rx-Timing-Deviation-Value-LCR											ProtocolIE-ID ::= 293
--WS extension
id-Unknown-294																ProtocolIE-ID ::= 294
id-DPC-Mode-Change-SupportIndicator											ProtocolIE-ID ::= 19
id-Unused-ProtocolIE-ID-247													ProtocolIE-ID ::= 247
id-Unused-ProtocolIE-ID-295													ProtocolIE-ID ::= 295
id-PrimaryCCPCH-RSCP-RL-ReconfPrepTDD										ProtocolIE-ID ::= 202
id-DL-TimeSlot-ISCP-Info-RL-ReconfPrepTDD									ProtocolIE-ID ::= 203
id-DL-Timeslot-ISCP-LCR-Information-RL-ReconfPrepTDD						ProtocolIE-ID ::= 204
id-DSCH-RNTI																ProtocolIE-ID ::= 249
id-DL-PowerBalancing-Information											ProtocolIE-ID ::= 296
id-DL-PowerBalancing-ActivationIndicator									ProtocolIE-ID ::= 297
id-DL-PowerBalancing-UpdatedIndicator										ProtocolIE-ID ::= 298
id-DL-ReferencePowerInformation												ProtocolIE-ID ::= 299
id-Enhanced-PrimaryCPICH-EcNo												ProtocolIE-ID ::= 224
id-IPDL-TDD-ParametersLCR													ProtocolIE-ID ::= 252
id-CellCapabilityContainer-FDD												ProtocolIE-ID ::= 300
id-CellCapabilityContainer-TDD												ProtocolIE-ID ::= 301
id-CellCapabilityContainer-TDD-LCR											ProtocolIE-ID ::= 302
id-RL-Specific-DCH-Info														ProtocolIE-ID ::= 317
id-RL-ReconfigurationRequestFDD-RL-InformationList 							ProtocolIE-ID ::= 318
id-RL-ReconfigurationRequestFDD-RL-Information-IEs							ProtocolIE-ID ::= 319
--WS extension
id-Unknown-320																ProtocolIE-ID ::= 320
id-RL-ReconfigurationRequestTDD-RL-Information								ProtocolIE-ID ::= 321
--WS extension
id-Unknown-322																ProtocolIE-ID ::= 322
id-CommonTransportChannelResourcesInitialisationNotRequired					ProtocolIE-ID ::= 250
id-DelayedActivation 														ProtocolIE-ID ::= 312
id-DelayedActivationList-RL-ActivationCmdFDD								ProtocolIE-ID ::= 313
id-DelayedActivationInformation-RL-ActivationCmdFDD							ProtocolIE-ID ::= 314
id-DelayedActivationList-RL-ActivationCmdTDD								ProtocolIE-ID ::= 315
id-DelayedActivationInformation-RL-ActivationCmdTDD							ProtocolIE-ID ::= 316
id-neighbouringTDDCellMeasurementInformationLCR								ProtocolIE-ID ::= 251
id-UL-SIR-Target-CCTrCH-InformationItem-RL-SetupRspTDD						ProtocolIE-ID ::= 150
id-UL-SIR-Target-CCTrCH-LCR-InformationItem-RL-SetupRspTDD					ProtocolIE-ID ::= 151
id-PrimCCPCH-RSCP-DL-PC-RqstTDD												ProtocolIE-ID ::= 451
id-HSDSCH-FDD-Information													ProtocolIE-ID ::= 452
id-HSDSCH-FDD-Information-Response											ProtocolIE-ID ::= 453
--WS extension
id-Unknown-454																ProtocolIE-ID ::= 454
id-Unknown-455																ProtocolIE-ID ::= 455
id-HSDSCH-FDD-Update-Information											ProtocolIE-ID ::= 466
id-HSDSCH-Information-to-Modify												ProtocolIE-ID ::= 456
id-HSDSCHMacdFlowSpecificInformationList-RL-PreemptRequiredInd				ProtocolIE-ID ::= 516
id-HSDSCHMacdFlowSpecificInformationItem-RL-PreemptRequiredInd				ProtocolIE-ID ::= 517
id-HSDSCH-RNTI																ProtocolIE-ID ::= 457
id-HSDSCH-TDD-Information													ProtocolIE-ID ::= 458
id-HSDSCH-TDD-Information-Response											ProtocolIE-ID ::= 459
--WS extension
id-Unknown-460																ProtocolIE-ID ::= 460
id-Unknown-461																ProtocolIE-ID ::= 461
id-Unknown-462																ProtocolIE-ID ::= 462
id-HSDSCH-TDD-Update-Information											ProtocolIE-ID ::= 467
id-HSPDSCH-RL-ID															ProtocolIE-ID ::= 463
id-HSDSCH-MACdFlows-to-Add 													ProtocolIE-ID ::= 531
id-HSDSCH-MACdFlows-to-Delete												ProtocolIE-ID ::= 532
id-Angle-Of-Arrival-Value-LCR												ProtocolIE-ID ::= 148
--WS extension
id-Unknown-149																ProtocolIE-ID ::= 149
id-TrafficClass																ProtocolIE-ID ::= 158
id-Unused-ProtocolIE-ID-248													ProtocolIE-ID ::= 248
id-Unused-ProtocolIE-ID-253													ProtocolIE-ID ::= 253
id-PDSCH-RL-ID																ProtocolIE-ID ::= 323
id-TimeSlot-RL-SetupRspTDD													ProtocolIE-ID ::= 325
--WS extension
id-Unknown-326																ProtocolIE-ID ::= 326
id-Unknown-327																ProtocolIE-ID ::= 327
id-Unknown-328																ProtocolIE-ID ::= 328
id-Unknown-329																ProtocolIE-ID ::= 329
id-Unknown-330																ProtocolIE-ID ::= 330
id-Unknown-331																ProtocolIE-ID ::= 331
id-Unknown-332																ProtocolIE-ID ::= 332
id-Unknown-333																ProtocolIE-ID ::= 333
id-Unknown-334																ProtocolIE-ID ::= 334
id-Unknown-335																ProtocolIE-ID ::= 335
id-Unknown-336																ProtocolIE-ID ::= 336
id-Unknown-337																ProtocolIE-ID ::= 337
id-Unknown-338																ProtocolIE-ID ::= 338
id-Unknown-339																ProtocolIE-ID ::= 339
id-Unknown-340																ProtocolIE-ID ::= 340
id-Unknown-341																ProtocolIE-ID ::= 341
id-Unknown-342																ProtocolIE-ID ::= 342
id-Unknown-343																ProtocolIE-ID ::= 343
id-Unknown-344																ProtocolIE-ID ::= 344
id-Unknown-345																ProtocolIE-ID ::= 345
id-Unknown-346																ProtocolIE-ID ::= 346
id-Unknown-347																ProtocolIE-ID ::= 347
id-Unknown-348																ProtocolIE-ID ::= 348
id-Unknown-349																ProtocolIE-ID ::= 349
id-Unknown-350																ProtocolIE-ID ::= 350
id-Unknown-351																ProtocolIE-ID ::= 351
id-Unknown-352																ProtocolIE-ID ::= 352
id-Unknown-353																ProtocolIE-ID ::= 353
id-Unknown-354																ProtocolIE-ID ::= 354
id-Unknown-355																ProtocolIE-ID ::= 355
id-Unknown-356																ProtocolIE-ID ::= 356
id-Unknown-357																ProtocolIE-ID ::= 357
id-Unknown-358																ProtocolIE-ID ::= 358
id-Unknown-359																ProtocolIE-ID ::= 359
id-Unknown-360																ProtocolIE-ID ::= 360
id-Unknown-361																ProtocolIE-ID ::= 361
id-Unknown-362																ProtocolIE-ID ::= 362
id-Unknown-363																ProtocolIE-ID ::= 363
id-Unknown-364																ProtocolIE-ID ::= 364
id-Unknown-365																ProtocolIE-ID ::= 365
id-Unknown-366																ProtocolIE-ID ::= 366
id-Unknown-367																ProtocolIE-ID ::= 367
id-Unknown-368																ProtocolIE-ID ::= 368
id-Unknown-369																ProtocolIE-ID ::= 369
id-Unknown-370																ProtocolIE-ID ::= 370
id-Unknown-371																ProtocolIE-ID ::= 371
id-Unknown-372																ProtocolIE-ID ::= 372
id-Unknown-373																ProtocolIE-ID ::= 373
id-Unknown-374																ProtocolIE-ID ::= 374
id-Unknown-375																ProtocolIE-ID ::= 375
id-Unknown-376																ProtocolIE-ID ::= 376
id-Unknown-377																ProtocolIE-ID ::= 377
id-Unknown-378																ProtocolIE-ID ::= 378
id-Unknown-379																ProtocolIE-ID ::= 379
id-Unknown-380																ProtocolIE-ID ::= 380
id-Unknown-381																ProtocolIE-ID ::= 381
id-Unknown-382																ProtocolIE-ID ::= 382
id-Unknown-383																ProtocolIE-ID ::= 383
id-Unknown-384																ProtocolIE-ID ::= 384
id-Unknown-385																ProtocolIE-ID ::= 385
id-Unknown-386																ProtocolIE-ID ::= 386
id-Unknown-387																ProtocolIE-ID ::= 387
id-Unknown-388																ProtocolIE-ID ::= 388
id-Unknown-389																ProtocolIE-ID ::= 389
id-Unknown-390																ProtocolIE-ID ::= 390
id-Unknown-391																ProtocolIE-ID ::= 391
id-Unknown-392																ProtocolIE-ID ::= 392
id-Unknown-393																ProtocolIE-ID ::= 393
id-Unknown-394																ProtocolIE-ID ::= 394
id-Unknown-395																ProtocolIE-ID ::= 395
id-Unknown-396																ProtocolIE-ID ::= 396
id-Unknown-397																ProtocolIE-ID ::= 397
id-Unknown-398																ProtocolIE-ID ::= 398
id-Unknown-399																ProtocolIE-ID ::= 399
id-Unknown-400																ProtocolIE-ID ::= 400
id-Unknown-401																ProtocolIE-ID ::= 401
id-Unknown-402																ProtocolIE-ID ::= 402
id-Unknown-403																ProtocolIE-ID ::= 403
id-Unknown-404																ProtocolIE-ID ::= 404
id-Unknown-405																ProtocolIE-ID ::= 405
id-Unknown-406																ProtocolIE-ID ::= 406
id-Unknown-407																ProtocolIE-ID ::= 407
id-Unknown-408																ProtocolIE-ID ::= 408
id-Unknown-409																ProtocolIE-ID ::= 409
id-Unknown-410																ProtocolIE-ID ::= 410
id-Unknown-411																ProtocolIE-ID ::= 411
id-Unknown-412																ProtocolIE-ID ::= 412
id-Unknown-413																ProtocolIE-ID ::= 413
id-Unknown-414																ProtocolIE-ID ::= 414
id-Unknown-415																ProtocolIE-ID ::= 415
id-Unknown-416																ProtocolIE-ID ::= 416
id-Unknown-417																ProtocolIE-ID ::= 417
id-Unknown-418																ProtocolIE-ID ::= 418
id-Unknown-419																ProtocolIE-ID ::= 419
id-Unknown-420																ProtocolIE-ID ::= 420
id-Unknown-421																ProtocolIE-ID ::= 421
id-Unknown-422																ProtocolIE-ID ::= 422
id-Unknown-423																ProtocolIE-ID ::= 423
id-Unknown-424																ProtocolIE-ID ::= 424
id-Unknown-425																ProtocolIE-ID ::= 425
id-Unknown-426																ProtocolIE-ID ::= 426
id-Unknown-427																ProtocolIE-ID ::= 427
id-Unknown-428																ProtocolIE-ID ::= 428
id-Unknown-429																ProtocolIE-ID ::= 429
id-Unknown-430																ProtocolIE-ID ::= 430
id-Unknown-431																ProtocolIE-ID ::= 431
id-Unknown-432																ProtocolIE-ID ::= 432
id-Unknown-433																ProtocolIE-ID ::= 433
id-Unknown-434																ProtocolIE-ID ::= 434
id-Unknown-435																ProtocolIE-ID ::= 435
id-Unknown-436																ProtocolIE-ID ::= 436
id-Unknown-437																ProtocolIE-ID ::= 437
id-Unknown-438																ProtocolIE-ID ::= 438
id-Unknown-439																ProtocolIE-ID ::= 439
id-Unknown-440																ProtocolIE-ID ::= 440
id-Unknown-441																ProtocolIE-ID ::= 441
id-Unknown-442																ProtocolIE-ID ::= 442
id-Unknown-443																ProtocolIE-ID ::= 443
id-Unknown-444																ProtocolIE-ID ::= 444
id-Unknown-445																ProtocolIE-ID ::= 445
id-Unknown-446																ProtocolIE-ID ::= 446
id-Unknown-447																ProtocolIE-ID ::= 447
id-Unknown-448																ProtocolIE-ID ::= 448
id-Unknown-449																ProtocolIE-ID ::= 449
id-Unknown-450																ProtocolIE-ID ::= 450
id-GERAN-Cell-Capability													ProtocolIE-ID ::= 468
id-GERAN-Classmark															ProtocolIE-ID ::= 469
id-DSCH-InitialWindowSize													ProtocolIE-ID ::= 480
id-UL-Synchronisation-Parameters-LCR										ProtocolIE-ID ::= 464
id-SNA-Information															ProtocolIE-ID ::= 479
id-MAChs-ResetIndicator														ProtocolIE-ID ::= 465
id-TDD-DL-DPCH-TimeSlotFormatModifyItem-LCR-RL-ReconfReadyTDD				ProtocolIE-ID ::= 481
id-TDD-UL-DPCH-TimeSlotFormatModifyItem-LCR-RL-ReconfReadyTDD				ProtocolIE-ID ::= 482
id-TDD-TPC-UplinkStepSize-LCR-RL-SetupRqstTDD								ProtocolIE-ID ::= 483
id-UL-CCTrCH-InformationList-RL-AdditionRqstTDD								ProtocolIE-ID ::= 484
id-UL-CCTrCH-InformationItem-RL-AdditionRqstTDD								ProtocolIE-ID ::= 485
id-DL-CCTrCH-InformationList-RL-AdditionRqstTDD								ProtocolIE-ID ::= 486
id-DL-CCTrCH-InformationItem-RL-AdditionRqstTDD								ProtocolIE-ID ::= 487
id-TDD-TPC-UplinkStepSize-InformationAdd-LCR-RL-ReconfPrepTDD				ProtocolIE-ID ::= 488
id-TDD-TPC-UplinkStepSize-InformationModify-LCR-RL-ReconfPrepTDD			ProtocolIE-ID ::= 489
id-TDD-TPC-DownlinkStepSize-InformationAdd-RL-ReconfPrepTDD					ProtocolIE-ID ::= 490
id-TDD-TPC-DownlinkStepSize-InformationModify-RL-ReconfPrepTDD				ProtocolIE-ID ::= 491
id-UL-TimingAdvanceCtrl-LCR													ProtocolIE-ID ::= 492
id-HSPDSCH-Timeslot-InformationList-PhyChReconfRqstTDD						ProtocolIE-ID ::= 493
id-HSPDSCH-Timeslot-InformationListLCR-PhyChReconfRqstTDD					ProtocolIE-ID ::= 494
id-HS-SICH-Reception-Quality 												ProtocolIE-ID ::= 495
id-HS-SICH-Reception-Quality-Measurement-Value 								ProtocolIE-ID ::= 496
id-HSSICH-Info-DM-Rprt														ProtocolIE-ID ::= 497
id-HSSICH-Info-DM-Rqst														ProtocolIE-ID ::= 498
id-HSSICH-Info-DM															ProtocolIE-ID ::= 499
id-CCTrCH-Maximum-DL-Power-RL-SetupRspTDD									ProtocolIE-ID ::= 500
id-CCTrCH-Minimum-DL-Power-RL-SetupRspTDD	ProtocolIE-ID ::= 501
id-CCTrCH-Maximum-DL-Power-RL-AdditionRspTDD								ProtocolIE-ID ::= 502
id-CCTrCH-Minimum-DL-Power-RL-AdditionRspTDD	ProtocolIE-ID ::= 503
id-CCTrCH-Maximum-DL-Power-RL-ReconfReadyTDD								ProtocolIE-ID ::= 504
id-CCTrCH-Minimum-DL-Power-RL-ReconfReadyTDD								ProtocolIE-ID ::= 505
id-Maximum-DL-Power-TimeslotLCR-InformationModifyItem-RL-ReconfReadyTDD		ProtocolIE-ID ::= 506
id-Minimum-DL-Power-TimeslotLCR-InformationModifyItem-RL-ReconfReadyTDD		ProtocolIE-ID ::= 507
id-DL-CCTrCH-InformationList-RL-ReconfRspTDD								ProtocolIE-ID ::= 508
id-DL-DPCH-InformationModifyItem-LCR-RL-ReconfRspTDD						ProtocolIE-ID ::= 509
id-Maximum-DL-Power-TimeslotLCR-InformationItem								ProtocolIE-ID ::= 510
id-Minimum-DL-Power-TimeslotLCR-InformationItem								ProtocolIE-ID ::= 511
id-TDD-Support-8PSK															ProtocolIE-ID ::= 512
id-TDD-maxNrDLPhysicalchannels												ProtocolIE-ID ::= 513
id-ExtendedGSMCellIndividualOffset											ProtocolIE-ID ::= 514
id-RL-ParameterUpdateIndicationFDD-RL-InformationList 						ProtocolIE-ID ::= 518
id-Primary-CPICH-Usage-For-Channel-Estimation								ProtocolIE-ID ::= 519
id-Secondary-CPICH-Information												ProtocolIE-ID ::= 520
id-Secondary-CPICH-Information-Change										ProtocolIE-ID ::= 521
id-Unused-ProtocolIE-ID-522													ProtocolIE-ID ::= 522
id-Unused-ProtocolIE-ID-523													ProtocolIE-ID ::= 523
id-RL-ParameterUpdateIndicationFDD-RL-Information-Item						ProtocolIE-ID ::= 524
id-Phase-Reference-Update-Indicator											ProtocolIE-ID ::= 525
id-Unidirectional-DCH-Indicator												ProtocolIE-ID ::= 526
id-RL-Information-RL-ReconfPrepTDD											ProtocolIE-ID ::= 527
id-Multiple-RL-InformationResponse-RL-ReconfReadyTDD						ProtocolIE-ID ::= 528
id-RL-ReconfigurationResponseTDD-RL-Information								ProtocolIE-ID ::= 529
id-Satellite-Almanac-Information-ExtItem									ProtocolIE-ID ::= 530
id-HSDSCH-Information-to-Modify-Unsynchronised								ProtocolIE-ID ::= 533
id-TnlQos																	ProtocolIE-ID ::= 534
id-RTLoadValue																ProtocolIE-ID ::= 535
id-NRTLoadInformationValue													ProtocolIE-ID ::= 536
id-CellPortionID															ProtocolIE-ID ::= 537
id-UpPTSInterferenceValue													ProtocolIE-ID ::= 538
id-PrimaryCCPCH-RSCP-Delta													ProtocolIE-ID ::= 539
id-UEMeasurementType														ProtocolIE-ID ::= 540
id-UEMeasurementTimeslotInfoHCR												ProtocolIE-ID ::= 541
id-UEMeasurementTimeslotInfoLCR												ProtocolIE-ID ::= 542
id-UEMeasurementReportCharacteristics										ProtocolIE-ID ::= 543
id-UEMeasurementParameterModAllow											ProtocolIE-ID ::= 544
id-UEMeasurementValueInformation											ProtocolIE-ID ::= 545
id-InterfacesToTraceItem													ProtocolIE-ID ::= 546
id-ListOfInterfacesToTrace													ProtocolIE-ID ::= 547
id-TraceDepth																ProtocolIE-ID ::= 548
id-TraceRecordingSessionReference											ProtocolIE-ID ::= 549
id-TraceReference															ProtocolIE-ID ::= 550
id-UEIdentity																ProtocolIE-ID ::= 551
id-NACC-Related-Data														ProtocolIE-ID ::= 552
id-GSM-Cell-InfEx-Rqst														ProtocolIE-ID ::= 553
id-MeasurementRecoveryBehavior												ProtocolIE-ID ::= 554
id-MeasurementRecoveryReportingIndicator									ProtocolIE-ID ::= 555
id-MeasurementRecoverySupportIndicator										ProtocolIE-ID ::= 556
id-DL-DPCH-Power-Information-RL-ReconfPrepFDD								ProtocolIE-ID ::= 557
id-F-DPCH-Information-RL-ReconfPrepFDD										ProtocolIE-ID ::= 558
id-F-DPCH-Information-RL-SetupRqstFDD										ProtocolIE-ID ::= 559
id-MBMS-Bearer-Service-List													ProtocolIE-ID ::= 560
id-MBMS-Bearer-Service-List-InfEx-Rsp										ProtocolIE-ID ::= 561
id-Active-MBMS-Bearer-ServiceFDD											ProtocolIE-ID ::= 562
id-Active-MBMS-Bearer-ServiceTDD											ProtocolIE-ID ::= 563
id-Old-URA-ID																ProtocolIE-ID ::= 564
--WS extension
id-Unknown-565																ProtocolIE-ID ::= 565
id-Unknown-566																ProtocolIE-ID ::= 566
id-Unknown-567																ProtocolIE-ID ::= 567
id-UE-State																	ProtocolIE-ID ::= 568
id-URA-ID																	ProtocolIE-ID ::= 569
--WS extension
id-Unknown-570																ProtocolIE-ID ::= 570
id-HARQ-Preamble-Mode														ProtocolIE-ID ::= 571
id-SynchronisationIndicator													ProtocolIE-ID ::= 572
id-UL-DPDCHIndicatorEDCH													ProtocolIE-ID ::= 573
id-EDPCH-Information														ProtocolIE-ID ::= 574
id-RL-Specific-EDCH-Information												ProtocolIE-ID ::= 575
id-EDCH-RL-Indication														ProtocolIE-ID ::= 576
id-EDCH-FDD-Information														ProtocolIE-ID ::= 577
id-EDCH-RLSet-Id															ProtocolIE-ID ::= 578
id-Serving-EDCHRL-Id														ProtocolIE-ID ::= 579
id-EDCH-FDD-DL-ControlChannelInformation									ProtocolIE-ID ::= 580
id-EDCH-FDD-InformationResponse												ProtocolIE-ID ::= 581
id-EDCH-MACdFlows-To-Add													ProtocolIE-ID ::= 582
id-EDCH-FDD-Information-To-Modify											ProtocolIE-ID ::= 583
id-EDCH-MACdFlows-To-Delete													ProtocolIE-ID ::= 584
id-EDPCH-Information-RLReconfRequest-FDD									ProtocolIE-ID ::= 585
id-EDCH-MacdFlowSpecificInformationList-RL-PreemptRequiredInd				ProtocolIE-ID ::= 586
id-EDCH-MacdFlowSpecificInformationItem-RL-PreemptRequiredInd				ProtocolIE-ID ::= 587
id-EDCH-MacdFlowSpecificInformationList-RL-CongestInd  						ProtocolIE-ID ::= 588
id-EDCH-MacdFlowSpecificInformationItem-RL-CongestInd						ProtocolIE-ID ::= 589
id-MBMS-Bearer-Service-Full-Address											ProtocolIE-ID ::= 590
id-Initial-DL-DPCH-TimingAdjustment											ProtocolIE-ID ::= 591
id-Initial-DL-DPCH-TimingAdjustment-Allowed									ProtocolIE-ID ::= 592
id-User-Plane-Congestion-Fields-Inclusion									ProtocolIE-ID ::= 593
id-HARQ-Preamble-Mode-Activation-Indicator									ProtocolIE-ID ::= 594
id-multiple-DedicatedMeasurementValueList-TDD-DM-Rsp						ProtocolIE-ID ::= 595
id-multiple-DedicatedMeasurementValueList-LCR-TDD-DM-Rsp					ProtocolIE-ID ::= 596
id-ProvidedInformation														ProtocolIE-ID ::= 597
id-Active-MBMS-Bearer-ServiceFDD-PFL										ProtocolIE-ID ::= 598
id-Active-MBMS-Bearer-ServiceTDD-PFL										ProtocolIE-ID ::= 599
id-FrequencyBandIndicator													ProtocolIE-ID ::= 600
id-Serving-cell-change-CFN													ProtocolIE-ID ::= 601
id-HS-DSCH-serving-cell-change-information									ProtocolIE-ID ::= 602
id-HS-DSCH-serving-cell-change-informationResponse							ProtocolIE-ID ::= 603
id-E-DCH-Serving-cell-change-informationResponse							ProtocolIE-ID ::= 604
id-secondary-LCR-CCPCH-Info-TDD												ProtocolIE-ID ::= 605
id-E-DCH-FDD-Update-Information												ProtocolIE-ID ::= 606
id-Inter-Frequency-Cell-List												ProtocolIE-ID ::= 607
id-Inter-Frequency-Cell-Information											ProtocolIE-ID ::= 608
id-multiple-HSSICHMeasurementValueList-TDD-DM-Rsp							ProtocolIE-ID ::= 609
id-TDD-Support-PLCCH														ProtocolIE-ID ::= 610
id-PLCCH-Information-UL-TimeslotLCR-Info									ProtocolIE-ID ::= 611
id-PLCCH-Information-PhyChReconfRqstTDD 									ProtocolIE-ID ::= 612
id-TDD768-maxNrDLPhysicalchannelsTS											ProtocolIE-ID ::= 613
id-RL-InformationResponse-RL-AdditionRspTDD768								ProtocolIE-ID ::= 614
id-UL-CCTrCH-InformationListIE-RL-AdditionRspTDD768							ProtocolIE-ID ::= 615
id-DL-CCTrCH-InformationListIE-RL-AdditionRspTDD768							ProtocolIE-ID ::= 616
id-UL-DPCH-InformationItem-RL-AdditionRspTDD768								ProtocolIE-ID ::= 617
id-DL-DPCH-InformationItem-RL-AdditionRspTDD768								ProtocolIE-ID ::= 618
id-UL-DPCH-InformationAddListIE-RL-ReconfReadyTDD768						ProtocolIE-ID ::= 619
id-UL-Timeslot-InformationModifyList-RL-ReconfReadyTDD768					ProtocolIE-ID ::= 620
id-DL-DPCH-InformationAddListIE-RL-ReconfReadyTDD768						ProtocolIE-ID ::= 621
id-DL-Timeslot-InformationModifyList-RL-ReconfReadyTDD768					ProtocolIE-ID ::= 622
id-secondary-CCPCH-Info-RL-ReconfReadyTDD768								ProtocolIE-ID ::= 623
id-hSSCCH-TDD-Specific-InfoList-Response768 								ProtocolIE-ID ::= 624
id-hSPDSCH-TDD-Specific-InfoList-Response768 								ProtocolIE-ID ::= 625
id-HSPDSCH-Timeslot-InformationList-PhyChReconfRqstTDD768					ProtocolIE-ID ::= 626
id-UL-Timeslot-InformationList-PhyChReconfRqstTDD768						ProtocolIE-ID ::= 627
id-DL-Timeslot-InformationList-PhyChReconfRqstTDD768						ProtocolIE-ID ::= 628
id-CellCapabilityContainer-TDD768											ProtocolIE-ID ::= 629
id-multiple-DedicatedMeasurementValueList-TDD768-DM-Rsp						ProtocolIE-ID ::= 630
id-neighbouringTDDCellMeasurementInformation768								ProtocolIE-ID ::= 631
id-UEMeasurementTimeslotInfo768												ProtocolIE-ID ::= 632
id-Rx-Timing-Deviation-Value-768											ProtocolIE-ID ::= 633
id-UEMeasurementValueTransmittedPowerList768								ProtocolIE-ID ::= 634
id-UEMeasurementValueTimeslotISCPList768									ProtocolIE-ID ::= 635
id-RL-InformationResponse-RL-SetupRspTDD768									ProtocolIE-ID ::= 636
id-UL-CCTrCH-InformationListIE-RL-SetupRspTDD768							ProtocolIE-ID ::= 637
id-DL-CCTrCH-InformationListIE-RL-SetupRspTDD768							ProtocolIE-ID ::= 638
id-UL-DPCH-InformationItem-RL-SetupRspTDD768								ProtocolIE-ID ::= 639
id-DL-DPCH-InformationItem-RL-SetupRspTDD768								ProtocolIE-ID ::= 640
id-TDD768-minimumSpreadingFactor-UL											ProtocolIE-ID ::= 641
id-TDD768-minimumSpreadingFactor-DL											ProtocolIE-ID ::= 642
id-TDD768-maxNrDLPhysicalchannels											ProtocolIE-ID ::= 643
id-DL-DPCH-InformationDeleteList768-RL-ReconfReadyTDD						ProtocolIE-ID ::= 644
id-DPCH-ID768-DM-Rsp														ProtocolIE-ID ::= 645
id-DPCH-ID768-DM-Rqst														ProtocolIE-ID ::= 646
id-DPCH-ID768-DM-Rprt														ProtocolIE-ID ::= 647
id-EDPCH-Information-RLAdditionReq-FDD										ProtocolIE-ID ::= 648
id-HSDSCH-Configured-Indicator												ProtocolIE-ID ::= 649
id-RxTimingDeviationForTAext												ProtocolIE-ID ::= 650
id-RxTimingDeviationForTA768												ProtocolIE-ID ::= 651
id-Rx-Timing-Deviation-Value-ext											ProtocolIE-ID ::= 652
id-E-DCH-PowerOffset-for-SchedulingInfo										ProtocolIE-ID ::= 653
id-TrCH-SrcStatisticsDescr													ProtocolIE-ID ::= 654
id-E-DCH-Information														ProtocolIE-ID ::= 655
id-E-DCH-Serving-RL-ID														ProtocolIE-ID ::= 656
id-E-DCH-Information-Reconfig												ProtocolIE-ID ::= 657
id-E-DCH-Information-Response												ProtocolIE-ID ::= 658
id-E-DCH-768-Information													ProtocolIE-ID ::= 659
id-E-DCH-768-Information-Reconfig											ProtocolIE-ID ::= 660
id-E-DCH-768-Information-Response											ProtocolIE-ID ::= 661
id-ExtendedPropagationDelay													ProtocolIE-ID ::= 662
id-Extended-Round-Trip-Time-Value											ProtocolIE-ID ::= 663
id-AlternativeFormatReportingIndicator										ProtocolIE-ID ::= 664
id-DCH-Indicator-For-E-DCH-HSDPA-Operation									ProtocolIE-ID ::= 665
id-E-RGCH-E-HICH-ChannelisationCodeValidityIndicator						ProtocolIE-ID ::= 666
id-E-DCH-Minimum-Set-E-TFCIValidityIndicator								ProtocolIE-ID ::= 667
id-Fast-Reconfiguration-Mode												ProtocolIE-ID ::= 668
id-Fast-Reconfiguration-Permission											ProtocolIE-ID ::= 669
id-Continuous-Packet-Connectivity-DTX-DRX-Information						ProtocolIE-ID ::= 670
id-Continuous-Packet-Connectivity-HS-SCCH-Less-Information					ProtocolIE-ID ::= 671
id-Continuous-Packet-Connectivity-HS-SCCH-Less-Information-Response			ProtocolIE-ID ::= 672
id-CPC-Information															ProtocolIE-ID ::= 673
--WS extension
id-Unknown-674																ProtocolIE-ID ::= 674
id-MIMO-InformationResponse													ProtocolIE-ID ::= 675
--WS extension
id-Unknown-676																ProtocolIE-ID ::= 676
id-E-DCH-LCR-Information													ProtocolIE-ID ::= 677
id-E-DCH-LCR-Information-Reconfig											ProtocolIE-ID ::= 678
id-E-DCH-LCR-Information-Response											ProtocolIE-ID ::= 679
id-HS-PDSCH-Code-Change-Grant												ProtocolIE-ID ::= 680
id-HS-PDSCH-Code-Change-Indicator											ProtocolIE-ID ::= 681
id-Extended-SRNC-ID															ProtocolIE-ID ::= 682
id-Extended-RNC-ID															ProtocolIE-ID ::= 683
id-SixtyfourQAM-DL-SupportIndicator											ProtocolIE-ID ::= 684
id-Enhanced-FACH-Support-Indicator											ProtocolIE-ID ::= 685
id-Enhanced-FACH-Information-ResponseFDD									ProtocolIE-ID ::= 686
--WS extension
id-Unknown-687																ProtocolIE-ID ::= 687
id-Unknown-688																ProtocolIE-ID ::= 688
id-Unknown-689																ProtocolIE-ID ::= 689
id-HSDSCH-MACdPDUSizeFormat													ProtocolIE-ID ::= 690
id-MaximumMACdPDU-SizeExtended												ProtocolIE-ID ::= 691
id-F-DPCH-SlotFormat														ProtocolIE-ID ::= 692
id-F-DPCH-SlotFormatSupportRequest											ProtocolIE-ID ::= 693
id-eDCH-MACdFlow-Retransmission-Timer-LCR									ProtocolIE-ID ::= 694
id-Max-UE-DTX-Cycle															ProtocolIE-ID ::= 695
--WS extension
id-Unknown-696																ProtocolIE-ID ::= 696
id-Unknown-697																ProtocolIE-ID ::= 697
id-Unknown-698																ProtocolIE-ID ::= 698
id-GANSS-Common-Data														ProtocolIE-ID ::= 699
id-GANSS-Information														ProtocolIE-ID ::= 700
id-GANSS-Generic-Data														ProtocolIE-ID ::= 701
id-TUTRANGANSSMeasurementThresholdInformation								ProtocolIE-ID ::= 702
id-TUTRANGANSSMeasurementValueInformation									ProtocolIE-ID ::= 703
--WS extension
id-Unknown-704																ProtocolIE-ID ::= 704
id-Ext-Reference-E-TFCI-PO													ProtocolIE-ID ::= 705
id-Ext-Max-Bits-MACe-PDU-non-scheduled										ProtocolIE-ID ::= 706
id-HARQ-MemoryPartitioningInfoExtForMIMO									ProtocolIE-ID ::= 707
id-MIMO-ActivationIndicator													ProtocolIE-ID ::= 708
id-MIMO-Mode-Indicator														ProtocolIE-ID ::= 709
id-MIMO-N-M-Ratio															ProtocolIE-ID ::= 710
id-TransportBearerNotSetupIndicator											ProtocolIE-ID ::= 711
id-TransportBearerNotRequestedIndicator										ProtocolIE-ID ::= 712
id-PowerControlGAP																ProtocolIE-ID ::= 713
id-UARFCNforNt																ProtocolIE-ID ::= 714
id-LCRTDD-uplink-Physical-Channel-Capability								ProtocolIE-ID ::= 715
id-number-Of-Supported-Carriers												ProtocolIE-ID ::= 716
id-HSSICH-SIRTarget																ProtocolIE-ID ::= 717
id-HSSICH-TPC-StepSize														ProtocolIE-ID ::= 718
id-tSN-Length																ProtocolIE-ID ::= 719
id-HS-SICH-ID-Extension														ProtocolIE-ID ::= 720
id-HSSICH-Info-DM-Rqst-Extension											ProtocolIE-ID ::= 721
id-multipleFreq-HSPDSCH-InformationList-ResponseTDDLCR						ProtocolIE-ID ::= 722
id-multicarrier-number														ProtocolIE-ID ::= 723
id-UPPCHPositionLCR															ProtocolIE-ID ::= 724
id-UpPCH-InformationList-LCRTDD												ProtocolIE-ID ::= 725
id-UpPCH-InformationItem-LCRTDD												ProtocolIE-ID ::= 726
id-Multiple-PLMN-List														ProtocolIE-ID ::= 727
id-UE-Capabilities-Info														ProtocolIE-ID ::= 728
id-FrameOffset																ProtocolIE-ID ::= 729
id-ChipOffset																ProtocolIE-ID ::= 730
id-Enhanced-PCH-Capability													ProtocolIE-ID ::= 731
id-SixteenQAM-UL-Operation-Indicator										ProtocolIE-ID ::= 732
id-E-TFCI-Boost-Information													ProtocolIE-ID ::= 733
id-SixtyfourQAM-UsageAllowedIndicator										ProtocolIE-ID ::= 734
id-SixtyfourQAM-DL-UsageIndicator											ProtocolIE-ID ::= 735
id-Default-Serving-Grant-in-DTX-Cycle2										ProtocolIE-ID ::= 736
id-E-DPDCH-PowerInterpolation												ProtocolIE-ID ::= 737
id-Extended-E-DCH-LCRTDD-PhysicalLayerCategory								ProtocolIE-ID ::= 738
id-E-DCH-MACdPDUSizeFormat													ProtocolIE-ID ::= 739
id-Continuous-Packet-Connectivity-HS-SCCH-Less-Deactivate-Indicator			ProtocolIE-ID ::= 740
id-E-DCH-DL-Control-Channel-Change-Information								ProtocolIE-ID ::= 741
id-E-DCH-DL-Control-Channel-Grant-Information								ProtocolIE-ID ::= 742
id-MaximumNumber-Of-Retransmission-For-SchedulingInfo-LCRTDD				ProtocolIE-ID ::= 743
id-E-DCH-RetransmissionTimer-For-SchedulingInfo-LCRTDD						ProtocolIE-ID ::= 744
id-E-PUCH-PowerControlGAP													ProtocolIE-ID ::= 745
id-HSDSCH-TBSizeTableIndicator												ProtocolIE-ID ::= 746
id-UE-with-enhanced-HS-SCCH-support-indicator								ProtocolIE-ID ::= 747
id-DGANSS-Corrections-Req													ProtocolIE-ID ::= 748
id-E-AGCH-Table-Choice														ProtocolIE-ID ::= 749
id-RANAP-EnhancedRelocationInformationRequest								ProtocolIE-ID ::= 750
id-RANAP-EnhancedRelocationInformationResponse								ProtocolIE-ID ::= 751
id-Common-EDCH-MAC-d-Flow-Specific-InformationFDD							ProtocolIE-ID ::= 752
id-Common-EDCH-Support-Indicator											ProtocolIE-ID ::= 753
id-E-RNTI																	ProtocolIE-ID ::= 754
id-Released-CN-Domain														ProtocolIE-ID ::= 755
id-MBMS-Bearer-Service-in-MBMS-Cell-InfEx-Rqst								ProtocolIE-ID ::= 756
id-MBMS-Bearer-Service-in-MBMS-Cell-InfEx-Rsp								ProtocolIE-ID ::= 757
id-MBMS-Bearer-Service-in-MBMS-Cell-InfEx-Rprt								ProtocolIE-ID ::= 758
id-MBMS-Cell-InfEx-Rqst														ProtocolIE-ID ::= 759
id-MBMS-Cell-InfEx-Rsp														ProtocolIE-ID ::= 760
id-MBMS-Cell-InfEx-Rprt														ProtocolIE-ID ::= 761
id-Counting-Information														ProtocolIE-ID ::= 762
id-Transmission-Mode-Information											ProtocolIE-ID ::= 763
id-MBMS-Neighbouring-Cell-Information										ProtocolIE-ID ::= 764
id-MBMS-RLC-Sequence-Number-Information										ProtocolIE-ID ::= 765
id-RLC-Sequence-Number														ProtocolIE-ID ::= 766
id-Neighbouring-E-UTRA-CellInformation										ProtocolIE-ID ::= 767
--WS extension
id-Unknown-768																ProtocolIE-ID ::= 768
id-MBSFN-Cluster-Identity													ProtocolIE-ID ::= 769
id-MCCH-Configuration-Info 													ProtocolIE-ID ::= 770
id-MCCH-Message-List 														ProtocolIE-ID ::= 771
id-MBSFN-Scheduling-Transmission-Time-Interval-Info-List					ProtocolIE-ID ::= 772
id-GANSS-Time-ID															ProtocolIE-ID ::= 773
id-GANSS-AddIonoModelReq													ProtocolIE-ID ::= 774
id-GANSS-EarthOrientParaReq													ProtocolIE-ID ::= 775
id-GANSS-AddNavigationModelsReq												ProtocolIE-ID ::= 776
id-GANSS-AddUTCModelsReq													ProtocolIE-ID ::= 777
id-GANSS-AuxInfoReq															ProtocolIE-ID ::= 778
id-GANSS-SBAS-ID															ProtocolIE-ID ::= 779
id-GANSS-ID																	ProtocolIE-ID ::= 780
id-GANSS-Additional-Ionospheric-Model										ProtocolIE-ID ::= 781
id-GANSS-Earth-Orientation-Parameters										ProtocolIE-ID ::= 782
id-GANSS-Additional-Time-Models												ProtocolIE-ID ::= 783
id-GANSS-Additional-Navigation-Models										ProtocolIE-ID ::= 784
id-GANSS-Additional-UTC-Models												ProtocolIE-ID ::= 785
id-GANSS-Auxiliary-Information												ProtocolIE-ID ::= 786
id-MinimumReducedE-DPDCH-GainFactor											ProtocolIE-ID ::= 787
id-Enhanced-FACH-Information-ResponseLCR									ProtocolIE-ID ::= 788
id-Common-EDCH-MAC-d-Flow-Specific-InformationLCR							ProtocolIE-ID ::= 789
id-HSDSCH-PreconfigurationSetup												ProtocolIE-ID ::= 790
id-HSDSCH-PreconfigurationInfo												ProtocolIE-ID ::= 791
id-NoOfTargetCellHS-SCCH-Order												ProtocolIE-ID ::= 792
id-EnhancedHSServingCC-Abort												ProtocolIE-ID ::= 793
id-Additional-HS-Cell-Information-RL-Setup									ProtocolIE-ID ::= 794
id-Additional-HS-Cell-Information-Response									ProtocolIE-ID ::= 795
id-Additional-HS-Cell-Information-RL-Addition								ProtocolIE-ID ::= 796
id-Additional-HS-Cell-Change-Information-Response							ProtocolIE-ID ::= 797
id-Additional-HS-Cell-Information-RL-Reconf-Prep							ProtocolIE-ID ::= 798
id-Additional-HS-Cell-Information-RL-Reconf-Req								ProtocolIE-ID ::= 799
id-Additional-HS-Cell-RL-Reconf-Response									ProtocolIE-ID ::= 800
id-Additional-HS-Cell-Information-RL-Param-Upd								ProtocolIE-ID ::= 801
id-Secondary-Serving-Cell-List												ProtocolIE-ID ::= 802
id-MultiCarrier-HSDSCH-Physical-Layer-Category 								ProtocolIE-ID ::= 803
id-IdleIntervalInformation													ProtocolIE-ID ::= 804
id-NeedforIdleInterval														ProtocolIE-ID ::= 805
id-IdleIntervalConfigurationIndicator										ProtocolIE-ID ::= 806
id-ContinuousPacketConnectivity-DRX-InformationLCR							ProtocolIE-ID ::= 807
id-ContinuousPacketConnectivity-DRX-Information-ResponseLCR					ProtocolIE-ID ::= 808
id-E-AGCH-UE-Inactivity-Monitor-Threshold									ProtocolIE-ID ::= 809
id-CPC-InformationLCR														ProtocolIE-ID ::= 810
id-E-DCH-Semi-PersistentScheduling-Information-LCR							ProtocolIE-ID ::= 811
id-HS-DSCH-Semi-PersistentScheduling-Information-LCR						ProtocolIE-ID ::= 812
id-HS-DSCH-Semi-PersistentScheduling-Information-ResponseLCR				ProtocolIE-ID ::= 813
id-E-DCH-Semi-PersistentScheduling-Information-ResponseLCR					ProtocolIE-ID ::= 814
id-MIMO-SFMode-For-HSPDSCHDualStream										ProtocolIE-ID ::= 815
id-MIMO-SFMode-Supported-For-HSPDSCHDualStream								ProtocolIE-ID ::= 816
id-MIMO-ReferenceSignal-InformationListLCR									ProtocolIE-ID ::= 817
id-GANSS-alm-keplerianNAVAlmanac											ProtocolIE-ID ::= 818
id-GANSS-alm-keplerianReducedAlmanac										ProtocolIE-ID ::= 819
id-GANSS-alm-keplerianMidiAlmanac											ProtocolIE-ID ::= 820
id-GANSS-alm-keplerianGLONASS												ProtocolIE-ID ::= 821
id-GANSS-alm-ecefSBASAlmanac												ProtocolIE-ID ::= 822
id-DL-RLC-PDU-Size-Format													ProtocolIE-ID ::= 823
id-MACes-Maximum-Bitrate-LCR												ProtocolIE-ID ::= 824
id-Single-Stream-MIMO-ActivationIndicator									ProtocolIE-ID ::= 825
id-Single-Stream-MIMO-Mode-Indicator										ProtocolIE-ID ::= 826
id-Dual-Band-Secondary-Serving-Cell-List									ProtocolIE-ID ::= 827
id-UE-AggregateMaximumBitRate												ProtocolIE-ID ::= 828
id-power-offset-for-S-CPICH-for-MIMO										ProtocolIE-ID ::= 829
id-power-offset-for-S-CPICH-for-MIMO-Request-Indicator						ProtocolIE-ID ::= 830
id-UE-SupportIndicatorExtension												ProtocolIE-ID ::= 831
--WS extension
id-Unknown-832																ProtocolIE-ID ::= 832
id-Unknown-833																ProtocolIE-ID ::= 833
id-Unknown-834																ProtocolIE-ID ::= 834
id-ActivationInformation													ProtocolIE-ID ::= 835
id-CellPortionLCRID															ProtocolIE-ID ::= 836
id-Additional-EDCH-Cell-Information-RL-Setup-Req							ProtocolIE-ID ::= 837
id-Additional-EDCH-Cell-Information-Response								ProtocolIE-ID ::= 838
id-Additional-EDCH-Cell-Information-RL-Add-Req								ProtocolIE-ID ::= 839
id-Additional-EDCH-Cell-Information-Response-RLAdd							ProtocolIE-ID ::= 840
id-Additional-EDCH-Cell-Information-RL-Reconf-Prep							ProtocolIE-ID ::= 841
id-Additional-EDCH-Cell-Information-RL-Reconf-Req							ProtocolIE-ID ::= 842
id-Additional-EDCH-Cell-Information-RL-Param-Upd							ProtocolIE-ID ::= 843
id-Additional-EDCH-Preconfiguration-Information								ProtocolIE-ID ::= 844
id-MulticellEDCH-Information												ProtocolIE-ID ::= 845
--WS extension
id-Unknown-846																ProtocolIE-ID ::= 846
id-Unknown-847																ProtocolIE-ID ::= 847
id-Unknown-848																ProtocolIE-ID ::= 848
id-Unknown-849																ProtocolIE-ID ::= 849
id-Unknown-850																ProtocolIE-ID ::= 850
id-Unknown-851																ProtocolIE-ID ::= 851
id-Unknown-852																ProtocolIE-ID ::= 852
id-Unknown-853																ProtocolIE-ID ::= 853
id-Additional-EDCH-Cell-Information-ResponseRLReconf						ProtocolIE-ID ::= 854
id-EDCH-Indicator															ProtocolIE-ID ::= 855
id-DiversityMode															ProtocolIE-ID ::= 856
id-TransmitDiversityIndicator												ProtocolIE-ID ::= 857
id-NonCellSpecificTxDiversity												ProtocolIE-ID ::= 858
id-CellCapabilityContainerExtension-FDD										ProtocolIE-ID ::= 859
id-HSDSCH-Physical-Layer-Category											ProtocolIE-ID ::= 860
id-E-RNTI-For-FACH															ProtocolIE-ID ::= 861
id-H-RNTI-For-FACH															ProtocolIE-ID ::= 862
id-RNTI-Allocation-Indicator												ProtocolIE-ID ::= 863
id-UE-AggregateMaximumBitRate-Enforcement-Indicator							ProtocolIE-ID ::= 864
id-DCH-MeasurementOccasion-Information										ProtocolIE-ID ::= 865
id-DCH-MeasurementType-Indicator											ProtocolIE-ID ::= 866
id-Out-of-Sychronization-Window												ProtocolIE-ID ::= 867
id-MulticellEDCH-RL-SpecificInformation										ProtocolIE-ID ::= 868
id-DGNSS-ValidityPeriod														ProtocolIE-ID ::= 869
id-TS0-HS-PDSCH-Indication-LCR 												ProtocolIE-ID ::= 870
id-UE-TS0-CapabilityLCR														ProtocolIE-ID ::= 871
id-Non-Serving-RL-Preconfig-Info											ProtocolIE-ID ::= 872
id-Non-Serving-RL-Preconfig-Setup											ProtocolIE-ID ::= 873
id-Non-Serving-RL-Preconfig-Removal											ProtocolIE-ID ::= 874
id-Additional-E-DCH-Non-Serving-RL-Preconfiguration-Setup					ProtocolIE-ID ::= 875
id-Additional-E-DCH-New-non-serving-RL-E-DCH-FDD-DL-Control-Channel-InfoList	ProtocolIE-ID ::= 876
id-CellListValidityIndicator												ProtocolIE-ID ::= 877

END
