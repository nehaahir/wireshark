-- RNSAP-PDU-Contents.asn
--
-- Taken from 3GPP TS 25.423  V9.4.0 (2010-09)
-- http://www.3gpp.org/ftp/Specs/archive/25_series/25.423/25423-790.zip/25423-790.DOC
--
-- 9.3.3	PDU Definitions
--
-- $Id: RNSAP-PDU-Contents.asn 52132 2013-09-18 02:48:29Z cmaynard $
--

-- **************************************************************
--
-- PDU definitions for RNSAP.
--
-- **************************************************************

RNSAP-PDU-Contents {
itu-t (0) identified-organization (4) etsi (0) mobileDomain (0)
umts-Access (20) modules (3) rnsap (1) version1 (1) rnsap-PDU-Contents (1) }

DEFINITIONS AUTOMATIC TAGS ::=

BEGIN

-- **************************************************************
--
-- IE parameter types from other modules.
--
-- **************************************************************

IMPORTS
	Active-Pattern-Sequence-Information,
	Active-MBMS-Bearer-Service-ListFDD,
	Active-MBMS-Bearer-Service-ListFDD-PFL,
	Active-MBMS-Bearer-Service-ListTDD,
	Active-MBMS-Bearer-Service-ListTDD-PFL,
	AllocationRetentionPriority,
	AllowedQueuingTime,
	Allowed-Rate-Information,
	AlphaValue,
	AlternativeFormatReportingIndicator,
	AntennaColocationIndicator,
	BLER,
	SCTD-Indicator,
	BindingID,
	C-ID,
	C-RNTI,
	CCTrCH-ID,
	CFN,
	CGI,
	ClosedLoopMode1-SupportIndicator,
	Closedlooptimingadjustmentmode,
	CN-CS-DomainIdentifier,
	CN-PS-DomainIdentifier,
	CNDomainType,
	Cause,
	CellCapabilityContainer-FDD,
	CellCapabilityContainerExtension-FDD,
	CellCapabilityContainer-TDD,
	CellCapabilityContainer-TDD-LCR,
	CellCapabilityContainer-TDD768,
	CellParameterID,
	CellPortionID,
	ChipOffset,
	CommonMeasurementAccuracy,
	CommonMeasurementType,
	CommonMeasurementValue,
	CommonMeasurementValueInformation,
	CommonTransportChannelResourcesInitialisationNotRequired,
	Common-EDCH-MAC-d-Flow-Specific-InformationFDD,
	Common-EDCH-Support-Indicator,
	CongestionCause,
	Continuous-Packet-Connectivity-DTX-DRX-Information,
	Continuous-Packet-Connectivity-HS-SCCH-Less-Information,
	Continuous-Packet-Connectivity-HS-SCCH-Less-Information-Response,
	CPC-Information,
	CoverageIndicator,
	CriticalityDiagnostics,
	CellPortionLCRID,
	D-RNTI,
	D-RNTI-ReleaseIndication,
	DCH-FDD-Information,
	DCH-ID,
	DCH-Indicator-For-E-DCH-HSDPA-Operation,
	DPCH-ID768,
	DCH-InformationResponse,
	DCH-TDD-Information,
	DL-DPCH-SlotFormat,
	DL-TimeslotISCP,
	DL-Power,
	DL-PowerBalancing-Information,
	DL-PowerBalancing-ActivationIndicator,
	DL-PowerBalancing-UpdatedIndicator,
	DL-ReferencePowerInformation,
	DL-ScramblingCode,
	DL-Timeslot-Information,
	DL-Timeslot-Information768,
	DL-TimeslotLCR-Information,
	DL-TimeSlot-ISCP-Info,
	DL-TimeSlot-ISCP-LCR-Information,
	DPC-Mode,
	DPC-Mode-Change-SupportIndicator,
	DPCH-ID,
	DL-DPCH-TimingAdjustment,
	DRXCycleLengthCoefficient,
	DedicatedMeasurementType,
	DedicatedMeasurementValue,
	DedicatedMeasurementValueInformation,
	DelayedActivation,
	DelayedActivationUpdate,
	DiversityControlField,
	DiversityMode,
	DSCH-FlowControlInformation,
	DSCH-FlowControlItem,
	DSCH-TDD-Information,
	DSCH-ID,
	DSCH-RNTI,
	EDCH-FDD-Information,
	EDCH-FDD-InformationResponse,
	EDCH-FDD-Information-To-Modify,
	EDCH-FDD-DL-ControlChannelInformation,
	EDCH-DDI-Value,
	EDCH-MACdFlow-ID,
	EDCH-MACdFlow-Specific-InfoList,
	EDCH-MACdFlows-To-Delete,
	EDCH-MACdFlows-Information,
	EDCH-RL-Indication,
	EDCH-Serving-RL,
	E-DCH-Serving-cell-change-informationResponse,
	EDPCH-Information-FDD,
	EDPCH-Information-RLReconfPrepare-FDD,
	EDPCH-Information-RLReconfRequest-FDD,
	E-DCH-FDD-Update-Information,
	E-DPCCH-PO,
	E-RGCH-2-IndexStepThreshold,
	E-RGCH-3-IndexStepThreshold,
	E-RNTI,
	E-TFCS-Information,
	E-TTI,
	Enhanced-FACH-Support-Indicator,
	Enhanced-FACH-Information-ResponseFDD,
	Enhanced-PCH-Capability,
	ExtendedPropagationDelay,
	Extended-RNC-ID,
	SchedulingPriorityIndicator,
	Enhanced-PrimaryCPICH-EcNo,
	F-DPCH-SlotFormat,
	F-DPCH-SlotFormatSupportRequest,
	FACH-FlowControlInformation,
	Fast-Reconfiguration-Mode,
	Fast-Reconfiguration-Permission,
	FDD-DCHs-to-Modify,
	FDD-DL-ChannelisationCodeNumber,
	FDD-DL-CodeInformation,
	FDD-TPC-DownlinkStepSize,
	FirstRLS-Indicator,
	FNReportingIndicator,
	FrameHandlingPriority,
	FrameOffset,
	GA-AccessPointPosition,
	GA-Cell,
	GA-CellAdditionalShapes,
	HARQ-Info-for-E-DCH,
	HCS-Prio,
	HSDSCH-Configured-Indicator,
	HSDSCH-FDD-Information,
	HSDSCH-FDD-Information-Response,
	HSDSCH-FDD-Update-Information,
	HSDSCH-TDD-Update-Information,
	HSDSCH-Information-to-Modify,
	HSDSCH-Information-to-Modify-Unsynchronised,
	HSDSCH-MACdFlow-ID,
	HSDSCH-MACdFlows-Information,
	HSDSCH-MACdFlows-to-Delete,
	HSDSCH-Physical-Layer-Category,
	HSDSCH-RNTI,
	HS-DSCH-serving-cell-change-information,
	HS-DSCH-serving-cell-change-informationResponse,
	HSDSCH-TDD-Information,
	HSDSCH-TDD-Information-Response,
	HS-SICH-ID,
	IMSI,
	InformationExchangeID,
	InformationReportCharacteristics,
	InformationType,
	Initial-DL-DPCH-TimingAdjustment-Allowed,
	InnerLoopDLPCStatus,
	Inter-Frequency-Cell-List,
	L3-Information,
	LimitedPowerIncrease,
	MaximumAllowedULTxPower,
	MaxNrDLPhysicalchannels,
	MaxNrDLPhysicalchannelsTS,
	MaxNrDLPhysicalchannels768,
	MaxNrDLPhysicalchannelsTS768,
	MaxNrOfUL-DPCHs,
	MaxNrTimeslots,
	MaxNrULPhysicalchannels,
	MACes-Guaranteed-Bitrate,
	MaxNr-Retransmissions-EDCH,
	Max-Set-E-DPDCHs,
	Max-UE-DTX-Cycle,
	MeasurementFilterCoefficient,
	MeasurementID,
	MeasurementRecoveryBehavior,
	MeasurementRecoveryReportingIndicator,
	MeasurementRecoverySupportIndicator,
	MBMS-Bearer-Service-List,
	MBSFN-Cluster-Identity,
	MCCH-Configuration-Info,
	MCCH-Message-List,
	MBSFN-Scheduling-Transmission-Time-Interval-Info-List,
	MidambleAllocationMode,
	MidambleShiftAndBurstType,
	MidambleShiftAndBurstType768,
	MidambleShiftLCR,
	MinimumSpreadingFactor,
	MinimumSpreadingFactor768,
	MinUL-ChannelisationCodeLength,
	Multiple-PLMN-List,
	MultiplexingPosition,
	NeighbouringFDDCellMeasurementInformation,
	NeighbouringTDDCellMeasurementInformation,
	NeighbouringTDDCellMeasurementInformation768,
	Neighbouring-GSM-CellInformation,
	Neighbouring-UMTS-CellInformation,
	NeighbouringTDDCellMeasurementInformationLCR,
	Neighbouring-E-UTRA-CellInformation,
	NrOfDLchannelisationcodes,
	PagingCause,
	PagingRecordType,
	PartialReportingIndicator,
	PayloadCRC-PresenceIndicator,
	PCCPCH-Power,
	PC-Preamble,
	Permanent-NAS-UE-Identity,
	Phase-Reference-Update-Indicator,
	PowerAdjustmentType,
	PowerOffset,
	PrimaryCCPCH-RSCP,
	PrimaryCPICH-EcNo,
	PrimaryCPICH-Power,
	Primary-CPICH-Usage-For-Channel-Estimation,
	PrimaryScramblingCode,
	PropagationDelay,
	ProvidedInformation,
	PunctureLimit,
	QE-Selector,
	RANAP-EnhancedRelocationInformationRequest,
	RANAP-EnhancedRelocationInformationResponse,
	RANAP-RelocationInformation,
	RB-Info,
	Released-CN-Domain,
	RL-ID,
	RL-Set-ID,
	RL-Specific-EDCH-Information,
	RNC-ID,
	RepetitionLength,
	RepetitionPeriod,
	ReportCharacteristics,
	Received-total-wide-band-power,
	RequestedDataValue,
	RequestedDataValueInformation,
	RL-Specific-DCH-Info,
	RxTimingDeviationForTA,
	RxTimingDeviationForTA768,
	S-RNTI,
	S-RNTI-Group,
	SCH-TimeSlot,
	SAI,
	SFN,
	Secondary-CCPCH-Info-TDD,
	Secondary-CCPCH-Info-TDD768,
	Secondary-CCPCH-System-Information-MBMS,
	Secondary-CPICH-Information,
	Secondary-CPICH-Information-Change,
	Secondary-LCR-CCPCH-Info-TDD,
	Secondary-Serving-Cell-List,
	SNA-Information,
	SpecialBurstScheduling,
	SSDT-SupportIndicator,
	STTD-SupportIndicator,
	AdjustmentPeriod,
	ScaledAdjustmentRatio,
	MaxAdjustmentStep,
	SRB-Delay,
	Support-8PSK,
	SyncCase,
	SynchronisationConfiguration,
	SixtyfourQAM-DL-SupportIndicator,
	TDD-ChannelisationCode,
	TDD-ChannelisationCode768,
	TDD-DCHs-to-Modify,
	TDD-DL-Code-Information,
	TDD-DPCHOffset,
	TDD-PhysicalChannelOffset,
	TDD-TPC-DownlinkStepSize,
	TDD-ChannelisationCodeLCR,
	TDD-DL-Code-LCR-Information,
	TDD-DL-Code-Information768,
	TDD-UL-Code-Information,
	TDD-UL-Code-LCR-Information,
	TDD-UL-Code-Information768,
	TFCI-Coding,
	TFCI-Presence,
	TFCI-SignallingMode,
	TimeSlot,
	TimeSlotLCR,
	TimingAdvanceApplied,
	TMGI,
	TnlQos,
	ToAWE,
	ToAWS,
	TraceDepth,
	TraceRecordingSessionReference,
	TraceReference,
	TrafficClass,
	TransmitDiversityIndicator,
	TransportBearerID,
	TransportBearerRequestIndicator,
	TFCS,
	Transmission-Gap-Pattern-Sequence-Information,
	TransportFormatManagement,
	TransportFormatSet,
	TransportLayerAddress,
	TrCH-SrcStatisticsDescr,
	TSTD-Indicator,
	TSTD-Support-Indicator,
	UARFCN,
	UC-ID,
	UE-AggregateMaximumBitRate,
	UEIdentity,
	UEMeasurementType,
	UEMeasurementTimeslotInfoHCR,
	UEMeasurementTimeslotInfoLCR,
	UEMeasurementTimeslotInfo768,
	UEMeasurementReportCharacteristics,
	UEMeasurementParameterModAllow,
	UEMeasurementValueInformation,
	UE-State,
	UL-DPCCH-SlotFormat,
	UL-DPDCHIndicatorEDCH,
	UL-SIR,
	UL-FP-Mode,
	UL-PhysCH-SF-Variation,
	UL-ScramblingCode,
	UL-Timeslot-Information,
	UL-Timeslot-Information768,
	UL-TimeslotLCR-Information,
	UL-TimeSlot-ISCP-Info,
	UL-TimeSlot-ISCP-LCR-Info,
	URA-ID,
	URA-Information,
	USCH-ID,
	USCH-Information,
	UL-Synchronisation-Parameters-LCR,
	TDD-DL-DPCH-TimeSlotFormat-LCR,
	TDD-UL-DPCH-TimeSlotFormat-LCR,
	MAChs-ResetIndicator,
	UL-TimingAdvanceCtrl-LCR,
	TDD-TPC-UplinkStepSize-LCR,
	PrimaryCCPCH-RSCP-Delta,
	SynchronisationIndicator,
	Support-PLCCH,
	PLCCHinformation,
	RxTimingDeviationForTAext,
	E-DCH-Information,
	E-DCH-Information-Reconfig,
	E-DCH-Information-Response,
	E-DCH-768-Information,
	E-DCH-768-Information-Reconfig,
	E-DCH-768-Information-Response,
	E-DCH-LCR-Information,
	E-DCH-LCR-Information-Reconfig,
	E-DCH-LCR-Information-Response,
	ControlGAP,
	IdleIntervalInformation,
	NeedforIdleInterval,
	HS-SICH-ID-Extension,
	TSN-Length,
	UPPCHPositionLCR,
	Common-EDCH-MAC-d-Flow-Specific-InformationLCR,
	Enhanced-FACH-Information-ResponseLCR,
	HSDSCH-PreconfigurationSetup,
	HSDSCH-PreconfigurationInfo,
	NoOfTargetCellHS-SCCH-Order,
	EnhancedHSServingCC-Abort,
	GANSS-Time-ID,
	HS-DSCH-FDD-Secondary-Serving-Update-Information,
	HS-DSCH-Secondary-Serving-Remove,
	HS-DSCH-FDD-Secondary-Serving-Information-To-Modify-Unsynchronised,
	HS-DSCH-Secondary-Serving-Information-To-Modify,
	HS-DSCH-Secondary-Serving-Cell-Change-Information-Response,
	HS-DSCH-FDD-Secondary-Serving-Information-Response,
	HS-DSCH-FDD-Secondary-Serving-Information,
	MinimumReducedE-DPDCH-GainFactor,
	ContinuousPacketConnectivity-DRX-InformationLCR,
	ContinuousPacketConnectivity-DRX-Information-ResponseLCR,
	CPC-InformationLCR,
	E-DCH-Semi-PersistentScheduling-Information-LCR,
	HS-DSCH-Semi-PersistentScheduling-Information-LCR,
	HS-DSCH-Semi-PersistentScheduling-Information-ResponseLCR,
	E-DCH-Semi-PersistentScheduling-Information-ResponseLCR,
	RNTI-Allocation-Indicator,
	ActivationInformation,
	Additional-EDCH-Setup-Info,
	Additional-EDCH-Cell-Information-Response-List,
	Additional-EDCH-FDD-Update-Information,
	Additional-EDCH-Cell-Information-To-Add-List,
	Additional-EDCH-Cell-Information-Response-RLReconf-List,
	DCH-MeasurementOccasion-Information,
	DCH-MeasurementType-Indicator,
	Setup-Or-ConfigurationChange-Or-Removal-Of-EDCH-On-secondary-UL-Frequency,
	Additional-EDCH-Cell-Information-Response-RLAddList,
	Non-Serving-RL-Preconfig-Setup,
	Non-Serving-RL-Preconfig-Info




FROM RNSAP-IEs

	PrivateIE-Container{},
	ProtocolExtensionContainer{},
	ProtocolIE-ContainerList{},
	ProtocolIE-ContainerPair{},
	ProtocolIE-ContainerPairList{},
	ProtocolIE-Container{},
	ProtocolIE-Single-Container{},
	RNSAP-PRIVATE-IES,
	RNSAP-PROTOCOL-EXTENSION,
	RNSAP-PROTOCOL-IES,
	RNSAP-PROTOCOL-IES-PAIR
FROM RNSAP-Containers

	maxCellsMeas,
	maxNoOfDSCHs,
	maxNoOfUSCHs,
	maxNrOfCCTrCHs,
	maxNrOfDCHs,
	maxNrOfTS,
	maxNrOfDPCHs,
	maxNrOfDPCHs768,
	maxNrOfDPCHsPerRL-1,
	maxNrOfDPCHs768PerRL-1,
	maxNrOfInterfaces,
	maxNrOfRLs,
	maxNrOfRLSets,
	maxNrOfRLSets-1,
	maxNrOfRLs-1,
	maxNrOfRLs-2,
	maxNrOfULTs,
	maxNrOfDLTs,
	maxResetContext,
	maxResetContextGroup,
	maxNoOfDSCHsLCR,
	maxNoOfUSCHsLCR,
	maxNrOfCCTrCHsLCR,
	maxNrOfTsLCR,
	maxNrOfDLTsLCR,
	maxNrOfULTsLCR,
	maxNrOfDPCHsLCR,
	maxNrOfDPCHsLCRPerRL-1,
	maxNrOfLCRTDDNeighboursPerRNC,
	maxNrOfMeasNCell,
	maxNrOfMACdFlows,
	maxNrOfMACdPDUSize,
	maxNrOfMCCHMessages,
	maxNrOfMBMSL3,
	maxNrOfEDCHMACdFlows,
	maxNrOfHSSICHs,
	maxNrOfHSSICHs-1,
	maxNrOfActiveMBMSServices,
	maxNrOfMBMSServices,
	maxNrofSigSeqERGHICH-1,
	maxNrOfCells,
	maxNrOfHSDSCH-1,
	maxNrOfEDCH-1,

	id-Active-MBMS-Bearer-ServiceFDD,
	id-Active-MBMS-Bearer-ServiceFDD-PFL,
	id-Active-MBMS-Bearer-ServiceTDD,
	id-Active-MBMS-Bearer-ServiceTDD-PFL,
	id-Active-Pattern-Sequence-Information,
	id-AdjustmentRatio,
	id-AllowedQueuingTime,
	id-AlternativeFormatReportingIndicator,
	id-AntennaColocationIndicator,
	id-BindingID,
	id-C-ID,
	id-C-RNTI,
	id-CFN,
	id-CFNReportingIndicator,
	id-CN-CS-DomainIdentifier,
	id-CN-PS-DomainIdentifier,
	id-Cause,
	id-CauseLevel-RL-AdditionFailureFDD,
	id-CauseLevel-RL-AdditionFailureTDD,
	id-CauseLevel-RL-ReconfFailure,
	id-CauseLevel-RL-SetupFailureFDD,
	id-CauseLevel-RL-SetupFailureTDD,
	id-CCTrCH-InformationItem-RL-FailureInd,
	id-CCTrCH-InformationItem-RL-RestoreInd,
	id-CellCapabilityContainer-FDD,
	id-CellCapabilityContainerExtension-FDD,
	id-CellCapabilityContainer-TDD,
	id-CellCapabilityContainer-TDD-LCR,
	id-CellPortionID,
	id-ChipOffset,
	id-ClosedLoopMode1-SupportIndicator,
	id-CNOriginatedPage-PagingRqst,
	id-CommonMeasurementAccuracy,
	id-CommonMeasurementObjectType-CM-Rprt,
	id-CommonMeasurementObjectType-CM-Rqst,
	id-CommonMeasurementObjectType-CM-Rsp,
	id-CommonMeasurementType,
	id-CommonTransportChannelResourcesInitialisationNotRequired,
	id-Common-EDCH-MAC-d-Flow-Specific-InformationFDD,
	id-Common-EDCH-Support-Indicator,
	id-CongestionCause,
	id-Continuous-Packet-Connectivity-DTX-DRX-Information,
	id-Continuous-Packet-Connectivity-HS-SCCH-Less-Information,
	id-Continuous-Packet-Connectivity-HS-SCCH-Less-Information-Response,
	id-CPC-Information,
	id-CoverageIndicator,
	id-CriticalityDiagnostics,
	id-CellPortionLCRID,
	id-D-RNTI,
	id-D-RNTI-ReleaseIndication,
	id-DCHs-to-Add-FDD,
	id-DCHs-to-Add-TDD,
	id-DCH-DeleteList-RL-ReconfPrepFDD,
	id-DCH-DeleteList-RL-ReconfPrepTDD,
	id-DCH-DeleteList-RL-ReconfRqstFDD,
	id-DCH-DeleteList-RL-ReconfRqstTDD,
	id-DCH-FDD-Information,
	id-DCH-TDD-Information,
	id-DCH-Indicator-For-E-DCH-HSDPA-Operation,
	id-FDD-DCHs-to-Modify,
	id-TDD-DCHs-to-Modify,
	id-DCH-InformationResponse,
	id-DCH-Rate-InformationItem-RL-CongestInd,
	id-DL-CCTrCH-InformationAddItem-RL-ReconfPrepTDD,
	id-DL-CCTrCH-InformationDeleteItem-RL-ReconfPrepTDD,
	id-DL-CCTrCH-InformationModifyItem-RL-ReconfPrepTDD,
	id-DL-CCTrCH-InformationListIE-RL-ReconfReadyTDD,
	id-DL-CCTrCH-InformationModifyItem-RL-ReconfRqstTDD,
	id-DL-CCTrCH-InformationDeleteItem-RL-ReconfRqstTDD,
	id-DL-CCTrCH-InformationItem-RL-SetupRqstTDD,
	id-DL-CCTrCH-InformationListIE-PhyChReconfRqstTDD,
	id-DL-CCTrCH-InformationListIE-RL-AdditionRspTDD,
	id-DL-CCTrCH-InformationListIE-RL-SetupRspTDD,
	id-DL-CCTrCH-InformationAddList-RL-ReconfPrepTDD,
	id-DL-CCTrCH-InformationDeleteList-RL-ReconfPrepTDD,
	id-DL-CCTrCH-InformationModifyList-RL-ReconfPrepTDD,
	id-DL-CCTrCH-InformationDeleteList-RL-ReconfRqstTDD,
	id-DL-CCTrCH-InformationModifyList-RL-ReconfRqstTDD,
	id-DL-CCTrCH-InformationList-RL-SetupRqstTDD,
	id-FDD-DL-CodeInformation,
	id-DL-DPCH-Information-RL-ReconfPrepFDD,
	id-DL-DPCH-Information-RL-SetupRqstFDD,
	id-DL-DPCH-Information-RL-ReconfRqstFDD,
	id-DL-DPCH-InformationItem-PhyChReconfRqstTDD,
	id-DL-DPCH-InformationItem-RL-AdditionRspTDD,
	id-DL-DPCH-InformationItem-RL-SetupRspTDD,
	id-DL-DPCH-InformationAddListIE-RL-ReconfReadyTDD,
	id-DL-DPCH-InformationDeleteListIE-RL-ReconfReadyTDD,
	id-DL-DPCH-InformationModifyListIE-RL-ReconfReadyTDD,
	id-DL-DPCH-TimingAdjustment,
	id-DL-DPCH-Power-Information-RL-ReconfPrepFDD,
	id-DL-Physical-Channel-Information-RL-SetupRqstTDD,
	id-DL-PowerBalancing-Information,
	id-DL-PowerBalancing-ActivationIndicator,
	id-DL-PowerBalancing-UpdatedIndicator,
	id-DL-ReferencePowerInformation,
	id-DLReferencePower,
	id-DLReferencePowerList-DL-PC-Rqst,
	id-DL-ReferencePowerInformation-DL-PC-Rqst,
	id-DRXCycleLengthCoefficient,
	id-DedicatedMeasurementObjectType-DM-Fail,
	id-DedicatedMeasurementObjectType-DM-Fail-Ind,
	id-DedicatedMeasurementObjectType-DM-Rprt,
	id-DedicatedMeasurementObjectType-DM-Rqst,
	id-DedicatedMeasurementObjectType-DM-Rsp,
	id-DedicatedMeasurementType,
	id-DelayedActivation,
	id-DelayedActivationList-RL-ActivationCmdFDD,
	id-DelayedActivationList-RL-ActivationCmdTDD,
	id-DelayedActivationInformation-RL-ActivationCmdFDD,
	id-DelayedActivationInformation-RL-ActivationCmdTDD,
	id-DPC-Mode,
	id-DPC-Mode-Change-SupportIndicator,
	id-DSCHs-to-Add-TDD,
	id-DSCH-DeleteList-RL-ReconfPrepTDD,
	id-DSCH-InformationListIE-RL-AdditionRspTDD,
	id-DSCH-InformationListIEs-RL-SetupRspTDD,
	id-DSCH-TDD-Information,
	id-DSCH-ModifyList-RL-ReconfPrepTDD,
	id-DSCH-RNTI,
	id-DSCHToBeAddedOrModifiedList-RL-ReconfReadyTDD,
	id-Dual-Band-Secondary-Serving-Cell-List,
	id-EDPCH-Information,
	id-EDCH-RL-Indication,
	id-EDCH-FDD-Information,
	id-Serving-EDCHRL-Id,
	id-EDCH-FDD-DL-ControlChannelInformation,
	id-EDCH-FDD-InformationResponse,
	id-E-DCH-FDD-Update-Information,
	id-EDCH-MACdFlows-To-Add,
	id-EDCH-FDD-Information-To-Modify,
	id-EDCH-MACdFlows-To-Delete,
	id-EDPCH-Information-RLReconfRequest-FDD,
	id-EDPCH-Information-RLAdditionReq-FDD,
	id-EDCH-MacdFlowSpecificInformationList-RL-PreemptRequiredInd,
	id-EDCH-MacdFlowSpecificInformationItem-RL-PreemptRequiredInd,
	id-EDCH-MacdFlowSpecificInformationList-RL-CongestInd,
	id-EDCH-MacdFlowSpecificInformationItem-RL-CongestInd,
	id-Enhanced-FACH-Support-Indicator,
	id-Enhanced-FACH-Information-ResponseFDD,
	id-Enhanced-PCH-Capability,
	id-ExtendedPropagationDelay,
	id-Extended-SRNC-ID,
	id-Extended-RNC-ID,
	id-Serving-cell-change-CFN,
	id-E-DCH-Serving-cell-change-informationResponse,
	id-E-RNTI-For-FACH,
	id-H-RNTI-For-FACH,
	id-RNTI-Allocation-Indicator,
	id-Enhanced-PrimaryCPICH-EcNo,
	id-E-RNTI,
	id-F-DPCH-SlotFormat,
	id-F-DPCH-SlotFormatSupportRequest,
	id-FACH-InfoForUESelectedS-CCPCH-CTCH-ResourceRspFDD,
	id-FACH-InfoForUESelectedS-CCPCH-CTCH-ResourceRspTDD,
	id-Fast-Reconfiguration-Mode,
	id-Fast-Reconfiguration-Permission,
	id-FrameOffset,
	id-F-DPCH-Information-RL-ReconfPrepFDD,
	id-F-DPCH-Information-RL-SetupRqstFDD,
	id-GA-Cell,
	id-GA-CellAdditionalShapes,
	id-GSM-Cell-InfEx-Rqst,
	id-HCS-Prio,
	id-HSDSCH-Configured-Indicator,
	id-HSDSCH-FDD-Information,
	id-HSDSCH-FDD-Information-Response,
	id-HSDSCH-FDD-Update-Information,
	id-HSDSCH-TDD-Update-Information,
	id-HSDSCH-Information-to-Modify,
	id-HSDSCH-Information-to-Modify-Unsynchronised,
	id-HSDSCH-MACdFlows-to-Add,
	id-HSDSCH-MACdFlows-to-Delete,
	id-HSDSCHMacdFlowSpecificInformationList-RL-PreemptRequiredInd,
	id-HSDSCHMacdFlowSpecificInformationItem-RL-PreemptRequiredInd,
	id-HSDSCH-Physical-Layer-Category,
	id-HSDSCH-RNTI,
	id-HS-DSCH-serving-cell-change-information,
	id-HS-DSCH-serving-cell-change-informationResponse,
	id-HSDSCH-TDD-Information,
	id-HSDSCH-TDD-Information-Response,
	id-HSPDSCH-RL-ID,
	id-HSPDSCH-Timeslot-InformationList-PhyChReconfRqstTDD,
	id-HSPDSCH-Timeslot-InformationListLCR-PhyChReconfRqstTDD,
	id-HSSICH-Info-DM-Rprt,
	id-HSSICH-Info-DM-Rqst,
	id-HSSICH-Info-DM,
	id-IMSI,
	id-InformationExchangeID,
	id-InformationExchangeObjectType-InfEx-Rprt,
	id-InformationExchangeObjectType-InfEx-Rqst,
	id-InformationExchangeObjectType-InfEx-Rsp,
	id-InformationReportCharacteristics,
	id-InformationType,
	id-Initial-DL-DPCH-TimingAdjustment,
	id-Initial-DL-DPCH-TimingAdjustment-Allowed,
	id-InnerLoopDLPCStatus,
	id-InterfacesToTraceItem,
	id-Inter-Frequency-Cell-List,
	id-L3-Information,
	id-AdjustmentPeriod,
	id-ListOfInterfacesToTrace,
	id-MaxAdjustmentStep,
	id-Max-UE-DTX-Cycle,
	id-MBMS-Bearer-Service-List,
	id-MBMS-Bearer-Service-List-InfEx-Rsp,
	id-MBMS-Bearer-Service-in-MBMS-Cell-InfEx-Rqst,
	id-MBMS-Bearer-Service-in-MBMS-Cell-InfEx-Rsp,
	id-MBMS-Bearer-Service-in-MBMS-Cell-InfEx-Rprt,
	id-MBMS-Cell-InfEx-Rqst,
	id-MBMS-Cell-InfEx-Rsp,
	id-MBMS-Cell-InfEx-Rprt,
	id-MBSFN-Cluster-Identity,
	id-MBSFN-Scheduling-Transmission-Time-Interval-Info-List,
	id-MCCH-Configuration-Info,
	id-MCCH-Message-List,
	id-MeasurementFilterCoefficient,
	id-MeasurementID,
	id-MeasurementRecoveryBehavior,
	id-MeasurementRecoveryReportingIndicator,
	id-MeasurementRecoverySupportIndicator,
	id-Multiple-PLMN-List,
	id-Multiple-RL-InformationResponse-RL-ReconfReadyTDD,
	id-NACC-Related-Data,
	id-Neighbouring-E-UTRA-CellInformation,
	id-Old-URA-ID,
	id-PagingArea-PagingRqst,
	id-PartialReportingIndicator,
	id-PDSCH-RL-ID,
	id-Permanent-NAS-UE-Identity,
	id-Phase-Reference-Update-Indicator,
	id-FACH-FlowControlInformation,
	id-PLCCH-Information-PhyChReconfRqstTDD,
	id-PowerAdjustmentType,
	id-PrimCCPCH-RSCP-DL-PC-RqstTDD,
	id-Primary-CPICH-Usage-For-Channel-Estimation,
	id-PropagationDelay,
	id-ProvidedInformation,
	id-RANAP-EnhancedRelocationInformationRequest,
	id-RANAP-EnhancedRelocationInformationResponse,
	id-RANAP-RelocationInformation,
	id-ResetIndicator,
	id-Released-CN-Domain,
	id-EDCH-RLSet-Id,
	id-RL-Information-PhyChReconfRqstFDD,
	id-RL-Information-PhyChReconfRqstTDD,
	id-RL-Information-RL-AdditionRqstFDD,
	id-RL-Information-RL-AdditionRqstTDD,
	id-RL-Information-RL-DeletionRqst,
	id-RL-Information-RL-FailureInd,
	id-RL-Information-RL-ReconfPrepFDD,
	id-RL-Information-RL-ReconfPrepTDD,
	id-RL-Information-RL-RestoreInd,
	id-RL-Information-RL-SetupRqstFDD,
	id-RL-Information-RL-SetupRqstTDD,
	id-RL-InformationItem-RL-CongestInd,
	id-RL-InformationItem-DM-Rprt,
	id-RL-InformationItem-DM-Rqst,
	id-RL-InformationItem-DM-Rsp,
	id-RL-InformationItem-RL-PreemptRequiredInd,
	id-RL-InformationItem-RL-SetupRqstFDD,
	id-RL-InformationList-RL-CongestInd,
	id-RL-InformationList-RL-AdditionRqstFDD,
	id-RL-InformationList-RL-DeletionRqst,
	id-RL-InformationList-RL-PreemptRequiredInd,
	id-RL-InformationList-RL-ReconfPrepFDD,
	id-RL-InformationResponse-RL-AdditionRspTDD,
	id-RL-InformationResponse-RL-ReconfReadyTDD,
	id-RL-InformationResponse-RL-ReconfRspTDD,
	id-RL-InformationResponse-RL-SetupRspTDD,
	id-RL-InformationResponseItem-RL-AdditionRspFDD,
	id-RL-InformationResponseItem-RL-ReconfReadyFDD,
	id-RL-InformationResponseItem-RL-ReconfRspFDD,
	id-RL-InformationResponseItem-RL-SetupRspFDD,
	id-RL-InformationResponseList-RL-AdditionRspFDD,
	id-RL-InformationResponseList-RL-ReconfReadyFDD,
	id-RL-InformationResponseList-RL-ReconfRspFDD,
	id-RL-InformationResponseList-RL-SetupRspFDD,
	id-RL-ParameterUpdateIndicationFDD-RL-Information-Item,
	id-RL-ParameterUpdateIndicationFDD-RL-InformationList,
	id-RL-ReconfigurationFailure-RL-ReconfFail,
	id-RL-ReconfigurationRequestFDD-RL-InformationList,
	id-RL-ReconfigurationRequestFDD-RL-Information-IEs,
	id-RL-ReconfigurationRequestTDD-RL-Information,
	id-RL-ReconfigurationResponseTDD-RL-Information,
	id-RL-Specific-DCH-Info,
	id-RL-Specific-EDCH-Information,
	id-RL-Set-InformationItem-DM-Rprt,
	id-RL-Set-InformationItem-DM-Rqst,
	id-RL-Set-InformationItem-DM-Rsp,
	id-RL-Set-Information-RL-FailureInd,
	id-RL-Set-Information-RL-RestoreInd,
	id-RL-Set-Successful-InformationItem-DM-Fail,
	id-RL-Set-Unsuccessful-InformationItem-DM-Fail,
	id-RL-Set-Unsuccessful-InformationItem-DM-Fail-Ind,
	id-RL-Successful-InformationItem-DM-Fail,
	id-RL-Unsuccessful-InformationItem-DM-Fail,
	id-RL-Unsuccessful-InformationItem-DM-Fail-Ind,
	id-ReportCharacteristics,
	id-Reporting-Object-RL-FailureInd,
	id-Reporing-Object-RL-RestoreInd,
	id-RNC-ID,
	id-RxTimingDeviationForTA,
	id-S-RNTI,
	id-SAI,
	id-Secondary-CPICH-Information,
	id-Secondary-CPICH-Information-Change,
	id-Secondary-Serving-Cell-List,
	id-Dual-Band-Secondary-Serving-Cell-List,
	id-SixtyfourQAM-DL-SupportIndicator,
	id-SFN,
	id-SFNReportingIndicator,
	id-SNA-Information,
	id-SRNC-ID,
	id-STTD-SupportIndicator,
	id-SuccessfulRL-InformationResponse-RL-AdditionFailureFDD,
	id-SuccessfulRL-InformationResponse-RL-SetupFailureFDD,
	id-TDD-maxNrDLPhysicalchannels,
	id-TDD-Support-8PSK,
	id-TDD-Support-PLCCH,
	id-timeSlot-ISCP,
	id-TimeSlot-RL-SetupRspTDD,
	id-TnlQos,
	id-TraceDepth,
	id-TraceRecordingSessionReference,
	id-TraceReference,
	id-TransportBearerID,
	id-TransportBearerRequestIndicator,
	id-TransportLayerAddress,
	id-UC-ID,
	id-ContextInfoItem-Reset,
	id-ContextGroupInfoItem-Reset,
	id-Transmission-Gap-Pattern-Sequence-Information,
	id-UE-AggregateMaximumBitRate,
	id-UEIdentity,
	id-UEMeasurementType,
	id-UEMeasurementTimeslotInfoHCR,
	id-UEMeasurementTimeslotInfoLCR,
	id-UEMeasurementReportCharacteristics,
	id-UEMeasurementParameterModAllow,
	id-UEMeasurementValueInformation,
	id-UE-State,
	id-UE-with-enhanced-HS-SCCH-support-indicator,
	id-UL-CCTrCH-AddInformation-RL-ReconfPrepTDD,
	id-UL-CCTrCH-DeleteInformation-RL-ReconfPrepTDD,
	id-UL-CCTrCH-ModifyInformation-RL-ReconfPrepTDD,
	id-UL-CCTrCH-InformationDeleteItem-RL-ReconfRqstTDD,
	id-UL-CCTrCH-InformationModifyItem-RL-ReconfRqstTDD,
	id-UL-CCTrCH-InformationAddList-RL-ReconfPrepTDD,
	id-UL-CCTrCH-InformationDeleteList-RL-ReconfPrepTDD,
	id-UL-CCTrCH-InformationModifyList-RL-ReconfPrepTDD,
	id-UL-CCTrCH-InformationDeleteList-RL-ReconfRqstTDD,
	id-UL-CCTrCH-InformationModifyList-RL-ReconfRqstTDD,
	id-UL-CCTrCH-InformationItem-RL-SetupRqstTDD,
	id-UL-CCTrCH-InformationList-RL-SetupRqstTDD,
	id-UL-CCTrCH-InformationListIE-PhyChReconfRqstTDD,
	id-UL-CCTrCH-InformationListIE-RL-AdditionRspTDD,
	id-UL-CCTrCH-InformationListIE-RL-ReconfReadyTDD,
	id-UL-CCTrCH-InformationListIE-RL-SetupRspTDD,
	id-UL-DPCH-Information-RL-ReconfPrepFDD,
	id-UL-DPCH-Information-RL-ReconfRqstFDD,
	id-UL-DPCH-Information-RL-SetupRqstFDD,
	id-UL-DPDCHIndicatorEDCH,
	id-UL-DPCH-InformationItem-PhyChReconfRqstTDD,
	id-UL-DPCH-InformationItem-RL-AdditionRspTDD,
	id-UL-DPCH-InformationItem-RL-SetupRspTDD,
	id-UL-DPCH-InformationAddListIE-RL-ReconfReadyTDD,
	id-UL-DPCH-InformationDeleteListIE-RL-ReconfReadyTDD,
	id-UL-DPCH-InformationModifyListIE-RL-ReconfReadyTDD,
	id-UL-Physical-Channel-Information-RL-SetupRqstTDD,
	id-UL-SIRTarget,
	id-URA-ID,
	id-URA-Information,
	id-UnsuccessfulRL-InformationResponse-RL-AdditionFailureFDD,
	id-UnsuccessfulRL-InformationResponse-RL-AdditionFailureTDD,
	id-UnsuccessfulRL-InformationResponse-RL-SetupFailureFDD,
	id-UnsuccessfulRL-InformationResponse-RL-SetupFailureTDD,
	id-USCHs-to-Add,
	id-USCH-DeleteList-RL-ReconfPrepTDD,
	id-USCH-InformationListIE-RL-AdditionRspTDD,
	id-USCH-InformationListIEs-RL-SetupRspTDD,
	id-USCH-Information,
	id-USCH-ModifyList-RL-ReconfPrepTDD,
	id-USCHToBeAddedOrModifiedList-RL-ReconfReadyTDD,
	id-DL-Timeslot-ISCP-LCR-Information-RL-SetupRqstTDD,
	id-RL-LCR-InformationResponse-RL-SetupRspTDD,
	id-UL-CCTrCH-LCR-InformationListIE-RL-SetupRspTDD,
	id-UL-DPCH-LCR-InformationItem-RL-SetupRspTDD,
	id-DL-CCTrCH-LCR-InformationListIE-RL-SetupRspTDD,
	id-DL-DPCH-LCR-InformationItem-RL-SetupRspTDD,
	id-DSCH-LCR-InformationListIEs-RL-SetupRspTDD,
	id-USCH-LCR-InformationListIEs-RL-SetupRspTDD,
	id-DL-Timeslot-ISCP-LCR-Information-RL-AdditionRqstTDD,
	id-RL-LCR-InformationResponse-RL-AdditionRspTDD,
	id-UL-CCTrCH-LCR-InformationListIE-RL-AdditionRspTDD,
	id-UL-DPCH-LCR-InformationItem-RL-AdditionRspTDD,
	id-DL-CCTrCH-LCR-InformationListIE-RL-AdditionRspTDD,
	id-DL-DPCH-LCR-InformationItem-RL-AdditionRspTDD,
	id-DSCH-LCR-InformationListIEs-RL-AdditionRspTDD,
	id-USCH-LCR-InformationListIEs-RL-AdditionRspTDD,
	id-UL-DPCH-LCR-InformationAddListIE-RL-ReconfReadyTDD,
	id-UL-Timeslot-LCR-InformationModifyList-RL-ReconfReadyTDD,
	id-DL-DPCH-LCR-InformationAddListIE-RL-ReconfReadyTDD,
	id-DL-Timeslot-LCR-InformationModifyList-RL-ReconfReadyTDD,
	id-UL-Timeslot-LCR-InformationList-PhyChReconfRqstTDD,
	id-DL-Timeslot-LCR-InformationList-PhyChReconfRqstTDD,
	id-timeSlot-ISCP-LCR-List-DL-PC-Rqst-TDD,
	id-TSTD-Support-Indicator-RL-SetupRqstTDD,
	id-PrimaryCCPCH-RSCP-RL-ReconfPrepTDD,
	id-DL-TimeSlot-ISCP-Info-RL-ReconfPrepTDD,
	id-DL-Timeslot-ISCP-LCR-Information-RL-ReconfPrepTDD,
	id-neighbouringTDDCellMeasurementInformationLCR,
	id-UL-SIR-Target-CCTrCH-InformationItem-RL-SetupRspTDD,
	id-UL-SIR-Target-CCTrCH-LCR-InformationItem-RL-SetupRspTDD,
	id-TrafficClass,
	id-UL-Synchronisation-Parameters-LCR,
	id-TDD-DL-DPCH-TimeSlotFormatModifyItem-LCR-RL-ReconfReadyTDD,
	id-TDD-UL-DPCH-TimeSlotFormatModifyItem-LCR-RL-ReconfReadyTDD,
	id-MAChs-ResetIndicator,
	id-UL-TimingAdvanceCtrl-LCR,
	id-CCTrCH-Maximum-DL-Power-RL-SetupRspTDD,
	id-CCTrCH-Minimum-DL-Power-RL-SetupRspTDD,
	id-CCTrCH-Maximum-DL-Power-RL-AdditionRspTDD,
	id-CCTrCH-Minimum-DL-Power-RL-AdditionRspTDD,
	id-CCTrCH-Maximum-DL-Power-RL-ReconfReadyTDD,
	id-CCTrCH-Minimum-DL-Power-RL-ReconfReadyTDD,
	id-Maximum-DL-Power-TimeslotLCR-InformationModifyItem-RL-ReconfReadyTDD,
	id-Minimum-DL-Power-TimeslotLCR-InformationModifyItem-RL-ReconfReadyTDD,
	id-DL-CCTrCH-InformationList-RL-ReconfRspTDD,
	id-DL-DPCH-InformationModifyItem-LCR-RL-ReconfRspTDD,
	id-TDD-TPC-UplinkStepSize-LCR-RL-SetupRqstTDD,
	id-UL-CCTrCH-InformationList-RL-AdditionRqstTDD,
	id-UL-CCTrCH-InformationItem-RL-AdditionRqstTDD,
	id-DL-CCTrCH-InformationList-RL-AdditionRqstTDD,
	id-DL-CCTrCH-InformationItem-RL-AdditionRqstTDD,
	id-TDD-TPC-UplinkStepSize-InformationAdd-LCR-RL-ReconfPrepTDD,
	id-TDD-TPC-UplinkStepSize-InformationModify-LCR-RL-ReconfPrepTDD,
	id-TDD-TPC-DownlinkStepSize-InformationAdd-RL-ReconfPrepTDD,
	id-TDD-TPC-DownlinkStepSize-InformationModify-RL-ReconfPrepTDD,
	id-PrimaryCCPCH-RSCP-Delta,
	id-multiple-DedicatedMeasurementValueList-TDD-DM-Rsp,
	id-multiple-DedicatedMeasurementValueList-LCR-TDD-DM-Rsp,
	id-SynchronisationIndicator,
	id-secondary-LCR-CCPCH-Info-TDD,
	id-multiple-HSSICHMeasurementValueList-TDD-DM-Rsp,
	id-CellCapabilityContainer-TDD768,
	id-neighbouringTDDCellMeasurementInformation768,
	id-RL-InformationResponse-RL-SetupRspTDD768,
	id-UL-CCTrCH-InformationListIE-RL-SetupRspTDD768,
	id-DL-CCTrCH-InformationListIE-RL-SetupRspTDD768,
	id-UL-DPCH-InformationItem-RL-SetupRspTDD768,
	id-DL-DPCH-InformationItem-RL-SetupRspTDD768,
	id-TDD768-minimumSpreadingFactor-UL,
	id-TDD768-minimumSpreadingFactor-DL,
	id-TDD768-maxNrDLPhysicalchannels,
	id-TDD768-maxNrDLPhysicalchannelsTS,
	id-RL-InformationResponse-RL-AdditionRspTDD768,
	id-UL-CCTrCH-InformationListIE-RL-AdditionRspTDD768,
	id-DL-CCTrCH-InformationListIE-RL-AdditionRspTDD768,
	id-UL-DPCH-InformationItem-RL-AdditionRspTDD768,
	id-DL-DPCH-InformationItem-RL-AdditionRspTDD768,
	id-UL-DPCH-InformationAddListIE-RL-ReconfReadyTDD768,
	id-UL-Timeslot-InformationModifyList-RL-ReconfReadyTDD768,
	id-DL-DPCH-InformationAddListIE-RL-ReconfReadyTDD768,
	id-DL-Timeslot-InformationModifyList-RL-ReconfReadyTDD768,
	id-secondary-CCPCH-Info-RL-ReconfReadyTDD768,
	id-HSPDSCH-Timeslot-InformationList-PhyChReconfRqstTDD768,
	id-UL-Timeslot-InformationList-PhyChReconfRqstTDD768,
	id-DL-Timeslot-InformationList-PhyChReconfRqstTDD768,
	id-multiple-DedicatedMeasurementValueList-TDD768-DM-Rsp,
	id-UEMeasurementTimeslotInfo768,
	id-DL-DPCH-InformationDeleteList768-RL-ReconfReadyTDD,
	id-DPCH-ID768-DM-Rsp,
	id-DPCH-ID768-DM-Rqst,
	id-DPCH-ID768-DM-Rprt,
	id-RxTimingDeviationForTAext,
	id-RxTimingDeviationForTA768,
	id-E-DCH-Information,
	id-E-DCH-Information-Reconfig,
	id-E-DCH-Serving-RL-ID,
	id-E-DCH-Information-Response,
	id-E-DCH-768-Information,
	id-E-DCH-768-Information-Reconfig,
	id-E-DCH-768-Information-Response,
	id-E-DCH-LCR-Information,
	id-E-DCH-LCR-Information-Reconfig,
	id-E-DCH-LCR-Information-Response,
	id-PowerControlGAP,
	id-IdleIntervalInformation,
	id-NeedforIdleInterval,
	id-IdleIntervalConfigurationIndicator,
	id-UARFCNforNt,
	id-HS-SICH-ID-Extension,
	id-HSSICH-Info-DM-Rqst-Extension,
	id-UPPCHPositionLCR,
	id-Common-EDCH-MAC-d-Flow-Specific-InformationLCR,
	id-Enhanced-FACH-Information-ResponseLCR,
	id-HSDSCH-PreconfigurationSetup,
	id-HSDSCH-PreconfigurationInfo,
	id-NoOfTargetCellHS-SCCH-Order,
	id-EnhancedHSServingCC-Abort,
	id-GANSS-Time-ID,
	id-Additional-HS-Cell-Information-RL-Setup,
	id-Additional-HS-Cell-Information-Response,
	id-Additional-HS-Cell-Information-RL-Addition,
	id-Additional-HS-Cell-Change-Information-Response,
	id-Additional-HS-Cell-Information-RL-Reconf-Prep,
	id-Additional-HS-Cell-Information-RL-Reconf-Req,
	id-Additional-HS-Cell-RL-Reconf-Response,
	id-Additional-HS-Cell-Information-RL-Param-Upd,
	id-MinimumReducedE-DPDCH-GainFactor,
	id-ContinuousPacketConnectivity-DRX-InformationLCR,
	id-ContinuousPacketConnectivity-DRX-Information-ResponseLCR,
	id-CPC-InformationLCR,
	id-E-DCH-Semi-PersistentScheduling-Information-LCR,
	id-HS-DSCH-Semi-PersistentScheduling-Information-LCR,
	id-HS-DSCH-Semi-PersistentScheduling-Information-ResponseLCR,
	id-E-DCH-Semi-PersistentScheduling-Information-ResponseLCR,
	id-ActivationInformation,
	id-Additional-EDCH-Cell-Information-RL-Setup-Req,
	id-Additional-EDCH-Cell-Information-Response,
	id-Additional-EDCH-Cell-Information-RL-Add-Req,
	id-Additional-EDCH-Cell-Information-Response-RLAdd,
	id-Additional-EDCH-Cell-Information-RL-Reconf-Prep,
	id-Additional-EDCH-Cell-Information-RL-Reconf-Req,
	id-Additional-EDCH-Cell-Information-RL-Param-Upd,
	id-Additional-EDCH-Cell-Information-ResponseRLReconf,
	id-DCH-MeasurementOccasion-Information,
	id-DCH-MeasurementType-Indicator,
	id-Non-Serving-RL-Preconfig-Info,
	id-Non-Serving-RL-Preconfig-Setup,
	id-Non-Serving-RL-Preconfig-Removal




FROM RNSAP-Constants;

-- **************************************************************
--
-- RADIO LINK SETUP REQUEST FDD
--
-- **************************************************************

RadioLinkSetupRequestFDD ::= SEQUENCE {
	protocolIEs                     ProtocolIE-Container       {{RadioLinkSetupRequestFDD-IEs}},
	protocolExtensions              ProtocolExtensionContainer {{RadioLinkSetupRequestFDD-Extensions}}                   OPTIONAL,
	...
}

RadioLinkSetupRequestFDD-IEs RNSAP-PROTOCOL-IES ::= {
	{ ID id-SRNC-ID					CRITICALITY reject	TYPE RNC-ID						PRESENCE mandatory} |
	{ ID id-S-RNTI					CRITICALITY reject	TYPE S-RNTI 					PRESENCE mandatory	} |
	{ ID id-D-RNTI					CRITICALITY reject	TYPE D-RNTI					PRESENCE optional	} |
	{ ID id-AllowedQueuingTime			CRITICALITY reject	TYPE AllowedQueuingTime 			PRESENCE optional	} |
	{ ID id-UL-DPCH-Information-RL-SetupRqstFDD	CRITICALITY reject	TYPE UL-DPCH-Information-RL-SetupRqstFDD		PRESENCE mandatory	} |
	{ ID id-DL-DPCH-Information-RL-SetupRqstFDD	CRITICALITY reject	TYPE DL-DPCH-Information-RL-SetupRqstFDD		PRESENCE optional	} |
	{ ID id-DCH-FDD-Information		CRITICALITY reject	TYPE DCH-FDD-Information		PRESENCE mandatory	} |
	{ ID id-RL-Information-RL-SetupRqstFDD		CRITICALITY notify	TYPE RL-InformationList-RL-SetupRqstFDD		PRESENCE mandatory	}|
	{ ID id-Transmission-Gap-Pattern-Sequence-Information		CRITICALITY reject	TYPE Transmission-Gap-Pattern-Sequence-Information	 PRESENCE optional } |
	{ ID id-Active-Pattern-Sequence-Information	CRITICALITY reject	TYPE Active-Pattern-Sequence-Information	 PRESENCE optional },
	...
}

UL-DPCH-Information-RL-SetupRqstFDD ::= SEQUENCE {
	ul-ScramblingCode				UL-ScramblingCode,
	minUL-ChannelisationCodeLength			MinUL-ChannelisationCodeLength,
	maxNrOfUL-DPCHs					MaxNrOfUL-DPCHs			OPTIONAL
	-- This IE shall be present if minUL-ChannelisationCodeLength equals to 4 -- ,
	ul-PunctureLimit				PunctureLimit,
	ul-TFCS							TFCS,
	ul-DPCCH-SlotFormat				UL-DPCCH-SlotFormat,
	ul-SIRTarget					UL-SIR			OPTIONAL,
	diversityMode					DiversityMode,
	not-Used-sSDT-CellIdLength		NULL			OPTIONAL,
	not-Used-s-FieldLength			NULL			OPTIONAL,
	iE-Extensions					ProtocolExtensionContainer { {UL-DPCH-Information-RL-SetupRqstFDD-ExtIEs} } OPTIONAL,
	...
}

UL-DPCH-Information-RL-SetupRqstFDD-ExtIEs RNSAP-PROTOCOL-EXTENSION ::= {
	{ ID id-DPC-Mode				CRITICALITY reject		EXTENSION DPC-Mode				PRESENCE optional }|
	{ ID id-UL-DPDCHIndicatorEDCH	CRITICALITY reject		EXTENSION UL-DPDCHIndicatorEDCH	PRESENCE optional },
	...
}

DL-DPCH-Information-RL-SetupRqstFDD ::= SEQUENCE {
	tFCS							TFCS,
	dl-DPCH-SlotFormat				DL-DPCH-SlotFormat,
	nrOfDLchannelisationcodes		NrOfDLchannelisationcodes,
	tFCI-SignallingMode				TFCI-SignallingMode,
	tFCI-Presence					TFCI-Presence			OPTIONAL
	-- This IE shall be present if DL DPCH Slot Format IE is equal to any of the values from 12 to 16 --,
	multiplexingPosition				MultiplexingPosition,
	powerOffsetInformation				PowerOffsetInformation-RL-SetupRqstFDD,
	fdd-dl-TPC-DownlinkStepSize		FDD-TPC-DownlinkStepSize,
	limitedPowerIncrease			LimitedPowerIncrease,
	innerLoopDLPCStatus				InnerLoopDLPCStatus,
	iE-Extensions					ProtocolExtensionContainer { {DL-DPCH-Information-RL-SetupRqstFDD-ExtIEs} } OPTIONAL,
	...
}

DL-DPCH-Information-RL-SetupRqstFDD-ExtIEs RNSAP-PROTOCOL-EXTENSION ::= {
	...
}

PowerOffsetInformation-RL-SetupRqstFDD ::= SEQUENCE {
		po1-ForTFCI-Bits				PowerOffset,
		po2-ForTPC-Bits					PowerOffset,
		po3-ForPilotBits				PowerOffset,
		iE-Extensions					ProtocolExtensionContainer { { PowerOffsetInformation-RL-SetupRqstFDD-ExtIEs} } OPTIONAL,
		...
}

PowerOffsetInformation-RL-SetupRqstFDD-ExtIEs RNSAP-PROTOCOL-EXTENSION ::= {
	...
}

RL-InformationList-RL-SetupRqstFDD 			::= SEQUENCE (SIZE (1..maxNrOfRLs)) OF ProtocolIE-Single-Container { {RL-InformationItemIEs-RL-SetupRqstFDD} }

RL-InformationItemIEs-RL-SetupRqstFDD RNSAP-PROTOCOL-IES ::= {
	{ ID id-RL-InformationItem-RL-SetupRqstFDD	CRITICALITY notify	TYPE RL-InformationItem-RL-SetupRqstFDD 		PRESENCE mandatory	}
}

RL-InformationItem-RL-SetupRqstFDD ::= SEQUENCE {
	rL-ID							RL-ID,
	c-ID							C-ID,
	firstRLS-indicator				FirstRLS-Indicator,
	frameOffset						FrameOffset,
	chipOffset						ChipOffset,
	propagationDelay				PropagationDelay		OPTIONAL,
	diversityControlField			DiversityControlField		OPTIONAL
	-- This IE shall be present if the RL is not the first one in the RL-InformationList-RL-SetupRqstFDD --,
	dl-InitialTX-Power				DL-Power			OPTIONAL,
	primaryCPICH-EcNo				PrimaryCPICH-EcNo			OPTIONAL,
	not-Used-sSDT-CellID			NULL			OPTIONAL,
	transmitDiversityIndicator		TransmitDiversityIndicator		OPTIONAL,
	-- This IE shall be present unless Diversity Mode IE in UL DPCH Information group is "none"
	iE-Extensions					ProtocolExtensionContainer { {RL-InformationItem-RL-SetupRqstFDD-ExtIEs} } OPTIONAL,
	...
}

RL-InformationItem-RL-SetupRqstFDD-ExtIEs RNSAP-PROTOCOL-EXTENSION ::= {
	{ ID id-Enhanced-PrimaryCPICH-EcNo	CRITICALITY ignore	EXTENSION Enhanced-PrimaryCPICH-EcNo	PRESENCE optional }|
	{ ID id-RL-Specific-DCH-Info	CRITICALITY ignore	EXTENSION RL-Specific-DCH-Info	PRESENCE optional }|
	{ ID id-DelayedActivation	CRITICALITY reject	EXTENSION DelayedActivation	PRESENCE optional }|
	{ ID id-CellPortionID	CRITICALITY ignore	EXTENSION CellPortionID 	PRESENCE optional }|
	{ ID id-RL-Specific-EDCH-Information	CRITICALITY reject	EXTENSION RL-Specific-EDCH-Information	PRESENCE optional }|
	{ ID id-EDCH-RL-Indication	CRITICALITY reject	EXTENSION EDCH-RL-Indication	PRESENCE optional }|
	{ ID id-ExtendedPropagationDelay	CRITICALITY ignore	EXTENSION ExtendedPropagationDelay 	PRESENCE optional }|
	{ ID id-SynchronisationIndicator	CRITICALITY reject	EXTENSION SynchronisationIndicator	PRESENCE optional }|
	{ ID id-HSDSCH-PreconfigurationSetup	CRITICALITY ignore	EXTENSION HSDSCH-PreconfigurationSetup	PRESENCE optional }|
	{ ID id-Non-Serving-RL-Preconfig-Setup	CRITICALITY ignore	EXTENSION Non-Serving-RL-Preconfig-Setup	PRESENCE optional },
	...
}

RadioLinkSetupRequestFDD-Extensions RNSAP-PROTOCOL-EXTENSION ::= {
	{ ID id-Permanent-NAS-UE-Identity	CRITICALITY ignore	EXTENSION Permanent-NAS-UE-Identity	PRESENCE optional }|
	{ ID id-DL-PowerBalancing-Information	CRITICALITY ignore	EXTENSION DL-PowerBalancing-Information	PRESENCE optional}|
	{ ID id-HSDSCH-FDD-Information	CRITICALITY reject	EXTENSION HSDSCH-FDD-Information		PRESENCE optional }|
	{ ID id-HSPDSCH-RL-ID	CRITICALITY reject	EXTENSION RL-ID	PRESENCE conditional }|
	-- This IE shall be present if HS-DSCH Information IE is present.
	{ ID id-MBMS-Bearer-Service-List	CRITICALITY notify	EXTENSION MBMS-Bearer-Service-List	PRESENCE optional }|
	{ ID id-EDPCH-Information	CRITICALITY reject	EXTENSION EDPCH-Information-FDD	PRESENCE optional }|
	{ ID id-EDCH-FDD-Information	CRITICALITY reject	EXTENSION EDCH-FDD-Information	PRESENCE conditional }|
	-- This IE is present if E-DPCH Information IE is present.
	{ ID id-Serving-EDCHRL-Id	CRITICALITY reject	EXTENSION EDCH-Serving-RL	PRESENCE optional }|
	-- This IE is present if E-DCHInformation IE is present.
	{ ID id-F-DPCH-Information-RL-SetupRqstFDD	CRITICALITY reject	EXTENSION F-DPCH-Information-RL-SetupRqstFDD	PRESENCE optional }|
	{ ID id-Initial-DL-DPCH-TimingAdjustment-Allowed	CRITICALITY ignore	EXTENSION Initial-DL-DPCH-TimingAdjustment-Allowed	PRESENCE optional }|
	{ ID id-DCH-Indicator-For-E-DCH-HSDPA-Operation	CRITICALITY reject	EXTENSION DCH-Indicator-For-E-DCH-HSDPA-Operation	PRESENCE optional }|
	{ ID id-Serving-cell-change-CFN	CRITICALITY reject	EXTENSION CFN			PRESENCE optional }|
	{ ID id-Continuous-Packet-Connectivity-DTX-DRX-Information	CRITICALITY reject	EXTENSION Continuous-Packet-Connectivity-DTX-DRX-Information								PRESENCE optional }|
	{ ID id-Continuous-Packet-Connectivity-HS-SCCH-Less-Information	CRITICALITY reject	EXTENSION Continuous-Packet-Connectivity-HS-SCCH-Less-Information					PRESENCE optional }|
	{ ID id-Extended-SRNC-ID	CRITICALITY reject	EXTENSION Extended-RNC-ID	PRESENCE optional }|
	{ ID id-Additional-HS-Cell-Information-RL-Setup	CRITICALITY reject	EXTENSION Additional-HS-Cell-Information-RL-Setup-List														PRESENCE optional }|
	{ ID id-UE-AggregateMaximumBitRate	CRITICALITY ignore	EXTENSION UE-AggregateMaximumBitRate	PRESENCE optional }|
	{ ID id-Additional-EDCH-Cell-Information-RL-Setup-Req	CRITICALITY reject	EXTENSION Additional-EDCH-Setup-Info			PRESENCE optional },
	...
}

Additional-HS-Cell-Information-RL-Setup-List	::= SEQUENCE (SIZE (1..maxNrOfHSDSCH-1)) OF Additional-HS-Cell-Information-RL-Setup-ItemIEs



Additional-HS-Cell-Information-RL-Setup-ItemIEs	::=SEQUENCE{
	hSPDSCH-RL-ID									RL-ID,
	c-ID											C-ID,
	hS-DSCH-FDD-Secondary-Serving-Information		HS-DSCH-FDD-Secondary-Serving-Information,
	iE-Extensions					ProtocolExtensionContainer { { Additional-HS-Cell-Information-RL-Setup-ItemIEs-ExtIEs} } OPTIONAL,
	...
}

Additional-HS-Cell-Information-RL-Setup-ItemIEs-ExtIEs	RNSAP-PROTOCOL-EXTENSION ::= {
	...
}

F-DPCH-Information-RL-SetupRqstFDD ::= SEQUENCE {
	powerOffsetInformation			PowerOffsetInformation-F-DPCH-RL-SetupRqstFDD,
	fdd-dl-TPC-DownlinkStepSize		FDD-TPC-DownlinkStepSize,
	limitedPowerIncrease			LimitedPowerIncrease,
	innerLoopDLPCStatus				InnerLoopDLPCStatus,
	iE-Extensions					ProtocolExtensionContainer { { F-DPCH-Information-RL-SetupRqstFDD-ExtIEs} }					OPTIONAL,
	...
}

F-DPCH-Information-RL-SetupRqstFDD-ExtIEs RNSAP-PROTOCOL-EXTENSION ::= {
	{ ID id-F-DPCH-SlotFormatSupportRequest		CRITICALITY reject			EXTENSION F-DPCH-SlotFormatSupportRequest		PRESENCE optional	}|
	{ ID id-F-DPCH-SlotFormat				CRITICALITY ignore	EXTENSION F-DPCH-SlotFormat		PRESENCE optional},
	...
}

PowerOffsetInformation-F-DPCH-RL-SetupRqstFDD ::= SEQUENCE {
	po2-ForTPC-Bits					PowerOffset,
	--This IE shall be ignored by DRNS
	iE-Extensions					ProtocolExtensionContainer { { PowerOffsetInformation-F-DPCH-RL-SetupRqstFDD-ExtIEs} }		OPTIONAL,
	...
}

PowerOffsetInformation-F-DPCH-RL-SetupRqstFDD-ExtIEs RNSAP-PROTOCOL-EXTENSION ::= {
	...
}

-- **************************************************************
--
-- RADIO LINK SETUP REQUEST TDD
--
-- **************************************************************

RadioLinkSetupRequestTDD ::= SEQUENCE {
	protocolIEs                     ProtocolIE-Container       {{RadioLinkSetupRequestTDD-IEs}},
	protocolExtensions              ProtocolExtensionContainer {{RadioLinkSetupRequestTDD-Extensions}}                   OPTIONAL,
	...
}

RadioLinkSetupRequestTDD-IEs RNSAP-PROTOCOL-IES ::= {
	{ ID id-SRNC-ID	CRITICALITY reject	TYPE RNC-ID	PRESENCE mandatory } |
	{ ID id-S-RNTI	CRITICALITY reject	TYPE S-RNTI 	PRESENCE mandatory } |
	{ ID id-D-RNTI	CRITICALITY reject	TYPE D-RNTI	PRESENCE optional } |
	{ ID id-UL-Physical-Channel-Information-RL-SetupRqstTDD	CRITICALITY reject	TYPE UL-Physical-Channel-Information-RL-SetupRqstTDD	PRESENCE mandatory } |
	{ ID id-DL-Physical-Channel-Information-RL-SetupRqstTDD	CRITICALITY reject	TYPE DL-Physical-Channel-Information-RL-SetupRqstTDD	PRESENCE mandatory } |
	{ ID id-AllowedQueuingTime	CRITICALITY reject	TYPE AllowedQueuingTime 	PRESENCE optional } |
	{ ID id-UL-CCTrCH-InformationList-RL-SetupRqstTDD	CRITICALITY notify	TYPE UL-CCTrCH-InformationList-RL-SetupRqstTDD	PRESENCE optional } |
	{ ID id-DL-CCTrCH-InformationList-RL-SetupRqstTDD	CRITICALITY notify	TYPE DL-CCTrCH-InformationList-RL-SetupRqstTDD	PRESENCE optional } |
	{ ID id-DCH-TDD-Information	CRITICALITY reject	TYPE DCH-TDD-Information 	PRESENCE optional } |
	{ ID id-DSCH-TDD-Information	CRITICALITY reject	TYPE DSCH-TDD-Information	PRESENCE optional } |
	{ ID id-USCH-Information	CRITICALITY reject	TYPE USCH-Information	PRESENCE optional } |
	{ ID id-RL-Information-RL-SetupRqstTDD	CRITICALITY reject	TYPE RL-Information-RL-SetupRqstTDD	PRESENCE mandatory },
	...
}

UL-Physical-Channel-Information-RL-SetupRqstTDD ::= SEQUENCE {
	maxNrTimeslots-UL				MaxNrTimeslots,
	minimumSpreadingFactor-UL		MinimumSpreadingFactor,
	maxNrULPhysicalchannels			MaxNrULPhysicalchannels,
	iE-Extensions					ProtocolExtensionContainer { {UL-Physical-Channel-InformationItem-RL-SetupRqstTDD-ExtIEs} } OPTIONAL,
	...
}

UL-Physical-Channel-InformationItem-RL-SetupRqstTDD-ExtIEs RNSAP-PROTOCOL-EXTENSION ::= {
	{ ID id-TDD-Support-8PSK		CRITICALITY ignore		EXTENSION Support-8PSK		PRESENCE optional	}|
	-- Applicable to 1.28Mcps TDD only
	{ ID id-TDD768-minimumSpreadingFactor-UL		CRITICALITY ignore			EXTENSION MinimumSpreadingFactor768		PRESENCE optional	},
	...
}

DL-Physical-Channel-Information-RL-SetupRqstTDD ::= SEQUENCE {
	maxNrTimeslots-DL				MaxNrTimeslots,
	minimumSpreadingFactor-DL		MinimumSpreadingFactor,
	maxNrDLPhysicalchannels			MaxNrDLPhysicalchannels,
	iE-Extensions					ProtocolExtensionContainer { {DL-Physical-Channel-InformationItem-RL-SetupRqstTDD-ExtIEs} } OPTIONAL,
	...
}

DL-Physical-Channel-InformationItem-RL-SetupRqstTDD-ExtIEs RNSAP-PROTOCOL-EXTENSION ::= {
	{ ID id-TDD-maxNrDLPhysicalchannels				CRITICALITY ignore			EXTENSION MaxNrDLPhysicalchannelsTS			PRESENCE optional	}|
	{ ID id-TDD-Support-8PSK						CRITICALITY ignore			EXTENSION Support-8PSK							PRESENCE optional	}|
	-- Applicable to 1.28Mcps TDD only
	{ ID id-TDD-Support-PLCCH						CRITICALITY ignore			EXTENSION Support-PLCCH							PRESENCE optional	}|
	{ ID id-TDD768-minimumSpreadingFactor-DL		CRITICALITY ignore			EXTENSION MinimumSpreadingFactor768			PRESENCE optional	}|
	{ ID id-TDD768-maxNrDLPhysicalchannels			CRITICALITY ignore			EXTENSION MaxNrDLPhysicalchannels768		PRESENCE optional	}|
	{ ID id-TDD768-maxNrDLPhysicalchannelsTS		CRITICALITY ignore			EXTENSION MaxNrDLPhysicalchannelsTS768		PRESENCE optional	},
	...
}

UL-CCTrCH-InformationList-RL-SetupRqstTDD			::= SEQUENCE (SIZE (1..maxNrOfCCTrCHs)) OF ProtocolIE-Single-Container { {UL-CCTrCH-InformationItemIEs-RL-SetupRqstTDD} }

UL-CCTrCH-InformationItemIEs-RL-SetupRqstTDD RNSAP-PROTOCOL-IES ::= {
	{ ID id-UL-CCTrCH-InformationItem-RL-SetupRqstTDD	CRITICALITY notify	TYPE UL-CCTrCH-InformationItem-RL-SetupRqstTDD 	PRESENCE mandatory	}
}

UL-CCTrCH-InformationItem-RL-SetupRqstTDD ::= SEQUENCE {
	cCTrCH-ID						CCTrCH-ID,
	ul-TFCS							TFCS,
	tFCI-Coding						TFCI-Coding,
	ul-PunctureLimit				PunctureLimit,
	iE-Extensions					ProtocolExtensionContainer { {UL-CCTrCH-InformationItem-RL-SetupRqstTDD-ExtIEs} } OPTIONAL,
	...
}

UL-CCTrCH-InformationItem-RL-SetupRqstTDD-ExtIEs RNSAP-PROTOCOL-EXTENSION ::= {
	{ ID id-TDD-TPC-UplinkStepSize-LCR-RL-SetupRqstTDD		CRITICALITY reject		EXTENSION	TDD-TPC-UplinkStepSize-LCR		PRESENCE optional	},
	-- Mandatory for 1.28Mcps TDD, not applicable to 3.84Mcps TDD or 7.68Mcps TDD
	...
}

DL-CCTrCH-InformationList-RL-SetupRqstTDD			::= SEQUENCE (SIZE (1..maxNrOfCCTrCHs)) OF ProtocolIE-Single-Container { {DL-CCTrCH-InformationItemIEs-RL-SetupRqstTDD} }

DL-CCTrCH-InformationItemIEs-RL-SetupRqstTDD RNSAP-PROTOCOL-IES ::= {
	{ ID id-DL-CCTrCH-InformationItem-RL-SetupRqstTDD	CRITICALITY notify	TYPE DL-CCTrCH-InformationItem-RL-SetupRqstTDD	PRESENCE mandatory	 }
}

DL-CCTrCH-InformationItem-RL-SetupRqstTDD ::= SEQUENCE {
	cCTrCH-ID						CCTrCH-ID,
	dl-TFCS							TFCS,
	tFCI-Coding						TFCI-Coding,
	dl-PunctureLimit				PunctureLimit,
	tdd-TPC-DownlinkStepSize		TDD-TPC-DownlinkStepSize,
	cCTrCH-TPCList					CCTrCH-TPCList-RL-SetupRqstTDD	OPTIONAL,
	iE-Extensions					ProtocolExtensionContainer { {DL-CCTrCH-InformationItem-RL-SetupRqstTDD-ExtIEs} } OPTIONAL,
	...
}

DL-CCTrCH-InformationItem-RL-SetupRqstTDD-ExtIEs RNSAP-PROTOCOL-EXTENSION ::= {
	...
}

CCTrCH-TPCList-RL-SetupRqstTDD ::= SEQUENCE (SIZE (1..maxNrOfCCTrCHs)) OF CCTrCH-TPCItem-RL-SetupRqstTDD

CCTrCH-TPCItem-RL-SetupRqstTDD	 ::= SEQUENCE {
	cCTrCH-ID							CCTrCH-ID,
	iE-Extensions						ProtocolExtensionContainer { { CCTrCH-TPCItem-RL-SetupRqstTDD-ExtIEs} } OPTIONAL,
	...
}

CCTrCH-TPCItem-RL-SetupRqstTDD-ExtIEs RNSAP-PROTOCOL-EXTENSION ::= {
	...
}

RL-Information-RL-SetupRqstTDD ::= SEQUENCE {
	rL-ID							RL-ID,
	c-ID							C-ID,
	frameOffset						FrameOffset,
	specialBurstScheduling			SpecialBurstScheduling,
	primaryCCPCH-RSCP				PrimaryCCPCH-RSCP		OPTIONAL,
	dL-TimeSlot-ISCP				DL-TimeSlot-ISCP-Info	OPTIONAL,
	--for 3.84Mcps TDD and 7.68Mcps TDD only
	iE-Extensions					ProtocolExtensionContainer { {RL-Information-RL-SetupRqstTDD-ExtIEs} } OPTIONAL,
	...
}

RL-Information-RL-SetupRqstTDD-ExtIEs RNSAP-PROTOCOL-EXTENSION ::= {
	{ ID id-DL-Timeslot-ISCP-LCR-Information-RL-SetupRqstTDD	CRITICALITY reject		EXTENSION 	DL-TimeSlot-ISCP-LCR-Information	PRESENCE optional	}|
	{ ID id-TSTD-Support-Indicator-RL-SetupRqstTDD				CRITICALITY ignore		EXTENSION 	TSTD-Support-Indicator				PRESENCE optional	}|
	--for 1.28Mcps TDD only
	{ ID id-RL-Specific-DCH-Info	CRITICALITY	ignore		EXTENSION 	RL-Specific-DCH-Info	PRESENCE 	optional	}|
	{ ID id-DelayedActivation CRITICALITY reject EXTENSION DelayedActivation PRESENCE optional }|
	{ ID id-UL-Synchronisation-Parameters-LCR			CRITICALITY	reject		EXTENSION 	UL-Synchronisation-Parameters-LCR		PRESENCE 	optional	}|	-- Mandatory for 1.28Mcps TDD, Not Applicable to 3.84Mcps TDD or 7.68Mcps TDD
	{ ID id-PrimaryCCPCH-RSCP-Delta		CRITICALITY	ignore		EXTENSION 	PrimaryCCPCH-RSCP-Delta		PRESENCE 	optional	}|
	{ ID id-IdleIntervalConfigurationIndicator							CRITICALITY ignore	EXTENSION	NULL				PRESENCE optional }|
	{ ID id-CellPortionLCRID	CRITICALITY ignore	EXTENSION CellPortionLCRID 	PRESENCE optional },
	...
}

RadioLinkSetupRequestTDD-Extensions RNSAP-PROTOCOL-EXTENSION ::= {
	{ ID id-Permanent-NAS-UE-Identity		CRITICALITY ignore	EXTENSION Permanent-NAS-UE-Identity	PRESENCE optional	}|
	{ ID id-HSDSCH-TDD-Information		CRITICALITY reject	EXTENSION HSDSCH-TDD-Information	PRESENCE optional	}|
	{ ID id-HSPDSCH-RL-ID		CRITICALITY reject	EXTENSION RL-ID	PRESENCE conditional	}|
	-- This IE shall be present if HS-DSCH Information IE is present.
	{ ID id-PDSCH-RL-ID		CRITICALITY ignore	EXTENSION RL-ID	PRESENCE optional }|
	{ ID id-MBMS-Bearer-Service-List		CRITICALITY notify	EXTENSION MBMS-Bearer-Service-List	PRESENCE optional}|
	{ ID id-E-DCH-Information		CRITICALITY reject	EXTENSION E-DCH-Information	PRESENCE optional }|
	{ ID id-E-DCH-Serving-RL-ID		CRITICALITY reject	EXTENSION RL-ID		PRESENCE optional	}|
	{ ID id-E-DCH-768-Information		CRITICALITY reject	EXTENSION E-DCH-768-Information	PRESENCE optional	}|
	{ ID id-E-DCH-LCR-Information		CRITICALITY reject	EXTENSION E-DCH-LCR-Information	PRESENCE optional	}|
	{ ID id-Extended-SRNC-ID		CRITICALITY reject	EXTENSION Extended-RNC-ID	PRESENCE optional }|
	{ ID id-ContinuousPacketConnectivity-DRX-InformationLCR	CRITICALITY reject	EXTENSION ContinuousPacketConnectivity-DRX-InformationLCR			PRESENCE optional }|
	{ ID id-HS-DSCH-Semi-PersistentScheduling-Information-LCR	CRITICALITY reject	EXTENSION HS-DSCH-Semi-PersistentScheduling-Information-LCR		PRESENCE optional }|
	{ ID id-E-DCH-Semi-PersistentScheduling-Information-LCR	CRITICALITY reject	EXTENSION E-DCH-Semi-PersistentScheduling-Information-LCR		PRESENCE optional }|
	{ ID id-RNTI-Allocation-Indicator							CRITICALITY ignore	EXTENSION  RNTI-Allocation-Indicator			PRESENCE optional }|
	{ ID id-DCH-MeasurementType-Indicator	CRITICALITY reject	EXTENSION DCH-MeasurementType-Indicator	PRESENCE optional },
	...
}

-- **************************************************************
--
-- RADIO LINK SETUP RESPONSE FDD
--
-- **************************************************************

RadioLinkSetupResponseFDD ::= SEQUENCE {
	protocolIEs                     ProtocolIE-Container       {{RadioLinkSetupResponseFDD-IEs}},
	protocolExtensions              ProtocolExtensionContainer {{RadioLinkSetupResponseFDD-Extensions}}                   OPTIONAL,
	...
}

RadioLinkSetupResponseFDD-IEs RNSAP-PROTOCOL-IES ::= {
	{ ID id-D-RNTI							CRITICALITY ignore	TYPE D-RNTI	PRESENCE optional	} |
	{ ID id-CN-PS-DomainIdentifier			CRITICALITY ignore	TYPE CN-PS-DomainIdentifier	PRESENCE optional	} |
	{ ID id-CN-CS-DomainIdentifier			CRITICALITY ignore	TYPE CN-CS-DomainIdentifier	PRESENCE optional	} |
	{ ID id-RL-InformationResponseList-RL-SetupRspFDD	CRITICALITY ignore	TYPE RL-InformationResponseList-RL-SetupRspFDD	PRESENCE mandatory	} |
	{ ID id-UL-SIRTarget					CRITICALITY ignore	TYPE UL-SIR	PRESENCE optional	} |
	{ ID id-CriticalityDiagnostics			CRITICALITY ignore	TYPE CriticalityDiagnostics	PRESENCE optional	},
	...
}

RL-InformationResponseList-RL-SetupRspFDD 		::= SEQUENCE (SIZE (1..maxNrOfRLs)) OF ProtocolIE-Single-Container { {RL-InformationResponseItemIEs-RL-SetupRspFDD} }

RL-InformationResponseItemIEs-RL-SetupRspFDD RNSAP-PROTOCOL-IES ::= {
	{ ID id-RL-InformationResponseItem-RL-SetupRspFDD	CRITICALITY ignore	TYPE RL-InformationResponseItem-RL-SetupRspFDD 	PRESENCE mandatory	}
}

RL-InformationResponseItem-RL-SetupRspFDD ::= SEQUENCE {
	rL-ID							RL-ID,
	rL-Set-ID						RL-Set-ID,
	uRA-Information					URA-Information		OPTIONAL,
	sAI								SAI,
	gA-Cell							GA-Cell		OPTIONAL,
	gA-AccessPointPosition			GA-AccessPointPosition		OPTIONAL,
	received-total-wide-band-power	Received-total-wide-band-power,
	not-Used-secondary-CCPCH-Info			NULL		OPTIONAL,
	dl-CodeInformation				FDD-DL-CodeInformation,
	diversityIndication				DiversityIndication-RL-SetupRspFDD,
	sSDT-SupportIndicator			SSDT-SupportIndicator,
	maxUL-SIR						UL-SIR,
	minUL-SIR						UL-SIR,
	closedlooptimingadjustmentmode	Closedlooptimingadjustmentmode			OPTIONAL,
	maximumAllowedULTxPower			MaximumAllowedULTxPower,
	maximumDLTxPower				DL-Power,
	minimumDLTxPower				DL-Power,
	primaryScramblingCode			PrimaryScramblingCode					OPTIONAL,
	uL-UARFCN						UARFCN									OPTIONAL,
	dL-UARFCN						UARFCN									OPTIONAL,
	primaryCPICH-Power				PrimaryCPICH-Power,
	not-Used-dSCHInformationResponse	NULL								OPTIONAL,
	neighbouring-UMTS-CellInformation	Neighbouring-UMTS-CellInformation	OPTIONAL,
	neighbouring-GSM-CellInformation	Neighbouring-GSM-CellInformation	OPTIONAL,
	pC-Preamble						PC-Preamble,
	sRB-Delay						SRB-Delay,
	iE-Extensions					ProtocolExtensionContainer { {RL-InformationResponseItem-RL-SetupRspFDD-ExtIEs} } OPTIONAL,
	...
}

RL-InformationResponseItem-RL-SetupRspFDD-ExtIEs RNSAP-PROTOCOL-EXTENSION ::= {
	{ ID id-GA-CellAdditionalShapes						CRITICALITY ignore	EXTENSION GA-CellAdditionalShapes								PRESENCE optional }|
	{ ID id-DL-PowerBalancing-ActivationIndicator		CRITICALITY ignore	EXTENSION DL-PowerBalancing-ActivationIndicator			PRESENCE optional }|
	{ ID id-HCS-Prio									CRITICALITY ignore	EXTENSION HCS-Prio													PRESENCE optional }|
	{ ID id-Primary-CPICH-Usage-For-Channel-Estimation	CRITICALITY ignore	EXTENSION Primary-CPICH-Usage-For-Channel-Estimation	PRESENCE optional }|
	{ ID id-Secondary-CPICH-Information					CRITICALITY ignore	EXTENSION Secondary-CPICH-Information						PRESENCE optional }|
	{ ID id-Active-MBMS-Bearer-ServiceFDD-PFL			CRITICALITY ignore	EXTENSION Active-MBMS-Bearer-Service-ListFDD-PFL			PRESENCE optional }|
	{ ID id-EDCH-RLSet-Id								CRITICALITY ignore	EXTENSION RL-Set-ID													PRESENCE optional }|
	{ ID id-EDCH-FDD-DL-ControlChannelInformation		CRITICALITY ignore	EXTENSION EDCH-FDD-DL-ControlChannelInformation			PRESENCE optional }|
	{ ID id-Initial-DL-DPCH-TimingAdjustment			CRITICALITY ignore	EXTENSION DL-DPCH-TimingAdjustment						PRESENCE optional }|
	{ ID id-F-DPCH-SlotFormat							CRITICALITY ignore	EXTENSION F-DPCH-SlotFormat						PRESENCE optional }|
	{ ID id-FrameOffset									CRITICALITY ignore	EXTENSION FrameOffset						PRESENCE optional }|
	{ ID id-ChipOffset									CRITICALITY ignore	EXTENSION ChipOffset												PRESENCE optional }|
	{ ID id-Neighbouring-E-UTRA-CellInformation			CRITICALITY ignore	EXTENSION Neighbouring-E-UTRA-CellInformation				PRESENCE optional }|
	{ ID id-HSDSCH-PreconfigurationInfo					CRITICALITY ignore	EXTENSION HSDSCH-PreconfigurationInfo						PRESENCE optional }|
	{ ID id-Non-Serving-RL-Preconfig-Info				CRITICALITY ignore	EXTENSION Non-Serving-RL-Preconfig-Info						PRESENCE optional },
	...
}

DiversityIndication-RL-SetupRspFDD ::= CHOICE {
	combining						Combining-RL-SetupRspFDD,
	nonCombiningOrFirstRL			NonCombiningOrFirstRL-RL-SetupRspFDD
}

Combining-RL-SetupRspFDD ::= SEQUENCE {
	rL-ID						RL-ID,
	iE-Extensions				ProtocolExtensionContainer { { CombiningItem-RL-SetupRspFDD-ExtIEs} } OPTIONAL,
	...
}

CombiningItem-RL-SetupRspFDD-ExtIEs RNSAP-PROTOCOL-EXTENSION ::= {
	{ ID id-DCH-InformationResponse			CRITICALITY ignore	EXTENSION DCH-InformationResponse					PRESENCE optional	}|
	{ ID id-EDCH-FDD-InformationResponse	CRITICALITY ignore	EXTENSION EDCH-FDD-InformationResponse			PRESENCE optional	},
	...
}

NonCombiningOrFirstRL-RL-SetupRspFDD ::= SEQUENCE {
	dCH-InformationResponse		DCH-InformationResponse,
	iE-Extensions				ProtocolExtensionContainer { { NonCombiningOrFirstRLItem-RL-SetupRspFDD-ExtIEs} } OPTIONAL,
	...
}

NonCombiningOrFirstRLItem-RL-SetupRspFDD-ExtIEs RNSAP-PROTOCOL-EXTENSION ::= {
	{ID id-EDCH-FDD-InformationResponse		CRITICALITY ignore	EXTENSION EDCH-FDD-InformationResponse			PRESENCE optional},
	...
}

RadioLinkSetupResponseFDD-Extensions RNSAP-PROTOCOL-EXTENSION ::= {
	{ ID id-HSDSCH-RNTI							CRITICALITY ignore		EXTENSION HSDSCH-RNTI									PRESENCE optional }|
	{ ID id-HSDSCH-FDD-Information-Response		CRITICALITY ignore		EXTENSION HSDSCH-FDD-Information-Response		PRESENCE optional }|
	{ ID id-Continuous-Packet-Connectivity-HS-SCCH-Less-Information-Response		CRITICALITY ignore		EXTENSION Continuous-Packet-Connectivity-HS-SCCH-Less-Information-Response		PRESENCE optional }|
	{ ID id-SixtyfourQAM-DL-SupportIndicator	CRITICALITY ignore		EXTENSION SixtyfourQAM-DL-SupportIndicator		PRESENCE optional }|
	{ ID id-Additional-HS-Cell-Information-Response	CRITICALITY ignore		EXTENSION Additional-HS-Cell-Information-Response-List		PRESENCE optional }|
	{ ID id-Additional-EDCH-Cell-Information-Response		CRITICALITY ignore	EXTENSION	Additional-EDCH-Cell-Information-Response-List			PRESENCE optional },
	...
}

Additional-HS-Cell-Information-Response-List	::= SEQUENCE (SIZE (1..maxNrOfHSDSCH-1)) OF Additional-HS-Cell-Information-Response-ItemIEs



Additional-HS-Cell-Information-Response-ItemIEs	::=SEQUENCE{
	hSPDSCH-RL-ID										RL-ID,
	hSDSCH-RNTI											HSDSCH-RNTI,
	hS-DSCH-FDD-Secondary-Serving-Information-Response	HS-DSCH-FDD-Secondary-Serving-Information-Response,
	sixtyfourQAM-DL-SupportIndicator					SixtyfourQAM-DL-SupportIndicator	OPTIONAL,
	iE-Extensions					ProtocolExtensionContainer { { Additional-HS-Cell-Information-Response-ItemIEs-ExtIEs} } OPTIONAL,
	...
}

Additional-HS-Cell-Information-Response-ItemIEs-ExtIEs	RNSAP-PROTOCOL-EXTENSION ::= {
	...
}

-- **************************************************************
--
-- RADIO LINK SETUP RESPONSE TDD
--
-- **************************************************************

RadioLinkSetupResponseTDD ::= SEQUENCE {
	protocolIEs                     ProtocolIE-Container       {{RadioLinkSetupResponseTDD-IEs}},
	protocolExtensions              ProtocolExtensionContainer {{RadioLinkSetupResponseTDD-Extensions}}                   OPTIONAL,
	...
}

RadioLinkSetupResponseTDD-IEs RNSAP-PROTOCOL-IES ::= {
	{ ID id-D-RNTI	CRITICALITY ignore	TYPE D-RNTI 	PRESENCE optional } |
	{ ID id-CN-PS-DomainIdentifier	CRITICALITY ignore	TYPE CN-PS-DomainIdentifier	PRESENCE optional } |
	{ ID id-CN-CS-DomainIdentifier	CRITICALITY ignore	TYPE CN-CS-DomainIdentifier	PRESENCE optional } |
	{ ID id-RL-InformationResponse-RL-SetupRspTDD	CRITICALITY ignore	TYPE RL-InformationResponse-RL-SetupRspTDD	PRESENCE optional } |
	--Mandatory for 3.84Mcps TDD only
	{ ID id-UL-SIRTarget	CRITICALITY ignore	TYPE UL-SIR	PRESENCE mandatory } |
	{ ID id-CriticalityDiagnostics	CRITICALITY ignore	TYPE CriticalityDiagnostics	PRESENCE optional },
	...
}

RL-InformationResponse-RL-SetupRspTDD ::= SEQUENCE {
	rL-ID						RL-ID,
	uRA-Information				URA-Information		OPTIONAL,
	sAI							SAI,
	gA-Cell						GA-Cell		OPTIONAL,
	gA-AccessPointPosition		GA-AccessPointPosition	OPTIONAL,
	ul-TimeSlot-ISCP-Info		UL-TimeSlot-ISCP-Info,
	maxUL-SIR					UL-SIR,
	minUL-SIR					UL-SIR,
	maximumAllowedULTxPower		MaximumAllowedULTxPower,
	maximumDLTxPower			DL-Power,
	minimumDLTxPower			DL-Power,
	uARFCNforNt					UARFCN				OPTIONAL,
	cellParameterID				CellParameterID		OPTIONAL,
	syncCase					SyncCase			OPTIONAL,
	sCH-TimeSlot				SCH-TimeSlot		OPTIONAL,
	-- This IE shall be present if Sync Case IE is equal to "Case2". --
	sCTD-Indicator				SCTD-Indicator	OPTIONAL,
	pCCPCH-Power				PCCPCH-Power,
	timingAdvanceApplied		TimingAdvanceApplied,
	alphaValue					AlphaValue,
	ul-PhysCH-SF-Variation		UL-PhysCH-SF-Variation,
	synchronisationConfiguration		SynchronisationConfiguration,
	secondary-CCPCH-Info-TDD			Secondary-CCPCH-Info-TDD	OPTIONAL,
	ul-CCTrCHInformation				UL-CCTrCHInformationList-RL-SetupRspTDD		OPTIONAL,
	dl-CCTrCHInformation				DL-CCTrCHInformationList-RL-SetupRspTDD		OPTIONAL,
	dCH-InformationResponse				DCH-InformationResponseList-RL-SetupRspTDD	OPTIONAL,
	dsch-InformationResponse			DSCH-InformationResponse-RL-SetupRspTDD OPTIONAL,
	usch-InformationResponse			USCH-InformationResponse-RL-SetupRspTDD OPTIONAL,
	neighbouring-UMTS-CellInformation			Neighbouring-UMTS-CellInformation OPTIONAL,
	neighbouring-GSM-CellInformation			Neighbouring-GSM-CellInformation OPTIONAL,
	iE-Extensions					ProtocolExtensionContainer { {RL-InformationResponse-RL-SetupRspTDD-ExtIEs} } OPTIONAL,
	...
}

RL-InformationResponse-RL-SetupRspTDD-ExtIEs RNSAP-PROTOCOL-EXTENSION ::= {
	{ ID id-GA-CellAdditionalShapes					CRITICALITY	ignore	EXTENSION	GA-CellAdditionalShapes					PRESENCE optional }|
	{ ID id-HCS-Prio								CRITICALITY	ignore	EXTENSION	HCS-Prio										PRESENCE optional }|
	{ ID id-TimeSlot-RL-SetupRspTDD					CRITICALITY ignore	EXTENSION	TimeSlot										PRESENCE conditional	}|
	-- This IE shall be present if Sync Case IE is Case1. --
	{ ID id-Neighbouring-E-UTRA-CellInformation		CRITICALITY ignore	EXTENSION Neighbouring-E-UTRA-CellInformation		PRESENCE optional },
	...
}

UL-CCTrCHInformationList-RL-SetupRspTDD ::= ProtocolIE-Single-Container {{UL-CCTrCHInformationListIEs-RL-SetupRspTDD}}

UL-CCTrCHInformationListIEs-RL-SetupRspTDD RNSAP-PROTOCOL-IES ::= {
	{ ID id-UL-CCTrCH-InformationListIE-RL-SetupRspTDD   CRITICALITY ignore	TYPE UL-CCTrCHInformationListIE-RL-SetupRspTDD		PRESENCE mandatory }
}

UL-CCTrCHInformationListIE-RL-SetupRspTDD ::= SEQUENCE (SIZE (1..maxNrOfCCTrCHs)) OF UL-CCTrCHInformationItem-RL-SetupRspTDD

UL-CCTrCHInformationItem-RL-SetupRspTDD ::= SEQUENCE {
	cCTrCH-ID					CCTrCH-ID,
	ul-DPCH-Information				UL-DPCH-InformationList-RL-SetupRspTDD		OPTIONAL,
	iE-Extensions					ProtocolExtensionContainer { {UL-CCTrCHInformationItem-RL-SetupRspTDD-ExtIEs} } OPTIONAL,
	...
}

UL-CCTrCHInformationItem-RL-SetupRspTDD-ExtIEs RNSAP-PROTOCOL-EXTENSION ::= {
	{ID id-UL-SIR-Target-CCTrCH-InformationItem-RL-SetupRspTDD		CRITICALITY ignore		EXTENSION UL-SIR		PRESENCE optional},
	...
}

UL-DPCH-InformationList-RL-SetupRspTDD ::= ProtocolIE-Single-Container { {UL-DPCH-InformationListIEs-RL-SetupRspTDD} }

UL-DPCH-InformationListIEs-RL-SetupRspTDD RNSAP-PROTOCOL-IES ::= {
	{ ID id-UL-DPCH-InformationItem-RL-SetupRspTDD		CRITICALITY ignore	TYPE UL-DPCH-InformationItem-RL-SetupRspTDD  PRESENCE mandatory	}
}


UL-DPCH-InformationItem-RL-SetupRspTDD ::= SEQUENCE {
	repetitionPeriod				RepetitionPeriod,
	repetitionLength				RepetitionLength,
	tDD-DPCHOffset					TDD-DPCHOffset,
	uL-Timeslot-Information			UL-Timeslot-Information,
	iE-Extensions					ProtocolExtensionContainer { {UL-DPCH-InformationItem-RL-SetupRspTDD-ExtIEs} } OPTIONAL,
	...
}

UL-DPCH-InformationItem-RL-SetupRspTDD-ExtIEs RNSAP-PROTOCOL-EXTENSION ::= {
	...
}

DL-CCTrCHInformationList-RL-SetupRspTDD ::= ProtocolIE-Single-Container {{DL-CCTrCHInformationListIEs-RL-SetupRspTDD}}

DL-CCTrCHInformationListIEs-RL-SetupRspTDD RNSAP-PROTOCOL-IES ::= {
	{ ID id-DL-CCTrCH-InformationListIE-RL-SetupRspTDD   CRITICALITY ignore	TYPE DL-CCTrCHInformationListIE-RL-SetupRspTDD  PRESENCE mandatory }
}

DL-CCTrCHInformationListIE-RL-SetupRspTDD ::= SEQUENCE (SIZE (1..maxNrOfCCTrCHs)) OF DL-CCTrCHInformationItem-RL-SetupRspTDD

DL-CCTrCHInformationItem-RL-SetupRspTDD ::= SEQUENCE {
	cCTrCH-ID						CCTrCH-ID,
	dl-DPCH-Information				DL-DPCH-InformationList-RL-SetupRspTDD		OPTIONAL,
	iE-Extensions					ProtocolExtensionContainer { {DL-CCTrCHInformationItem-RL-SetupRspTDD-ExtIEs} } OPTIONAL,
	...
}

DL-CCTrCHInformationItem-RL-SetupRspTDD-ExtIEs RNSAP-PROTOCOL-EXTENSION ::= {
	{ ID id-CCTrCH-Maximum-DL-Power-RL-SetupRspTDD	CRITICALITY ignore	EXTENSION  DL-Power	PRESENCE optional }| -- this is a DCH type CCTrCH power
	{ ID id-CCTrCH-Minimum-DL-Power-RL-SetupRspTDD	CRITICALITY ignore	EXTENSION  DL-Power	PRESENCE optional }, -- this is a DCH type CCTrCH power
	...
}

DL-DPCH-InformationList-RL-SetupRspTDD ::= ProtocolIE-Single-Container { {DL-DPCH-InformationListIEs-RL-SetupRspTDD} }

DL-DPCH-InformationListIEs-RL-SetupRspTDD RNSAP-PROTOCOL-IES ::= {
	{ ID id-DL-DPCH-InformationItem-RL-SetupRspTDD		CRITICALITY ignore	TYPE DL-DPCH-InformationItem-RL-SetupRspTDD  PRESENCE mandatory	}
}

DL-DPCH-InformationItem-RL-SetupRspTDD ::= SEQUENCE {
	repetitionPeriod				RepetitionPeriod,
	repetitionLength				RepetitionLength,
	tDD-DPCHOffset					TDD-DPCHOffset,
	dL-Timeslot-Information			DL-Timeslot-Information,
	iE-Extensions					ProtocolExtensionContainer { {DL-DPCH-InformationItem-RL-SetupRspTDD-ExtIEs} } OPTIONAL,
	...
}

DL-DPCH-InformationItem-RL-SetupRspTDD-ExtIEs RNSAP-PROTOCOL-EXTENSION ::= {
	...
}

DCH-InformationResponseList-RL-SetupRspTDD ::= ProtocolIE-Single-Container {{DCH-InformationResponseListIEs-RL-SetupRspTDD}}

DCH-InformationResponseListIEs-RL-SetupRspTDD RNSAP-PROTOCOL-IES ::= {
	{ ID id-DCH-InformationResponse   CRITICALITY ignore	TYPE DCH-InformationResponse  PRESENCE mandatory }
}

DSCH-InformationResponse-RL-SetupRspTDD ::= ProtocolIE-Single-Container {{DSCH-InformationList-RL-SetupRspTDD}}

DSCH-InformationList-RL-SetupRspTDD RNSAP-PROTOCOL-IES ::= {
	{ ID id-DSCH-InformationListIEs-RL-SetupRspTDD		CRITICALITY ignore	TYPE DSCH-InformationListIEs-RL-SetupRspTDD PRESENCE mandatory }
}

DSCH-InformationListIEs-RL-SetupRspTDD ::= SEQUENCE (SIZE(0..maxNoOfDSCHs)) OF DSCHInformationItem-RL-SetupRspTDD

DSCHInformationItem-RL-SetupRspTDD ::= SEQUENCE {
	dsch-ID					DSCH-ID,
	dSCH-FlowControlInformation		DSCH-FlowControlInformation,
	bindingID				BindingID	OPTIONAL,
	transportLayerAddress	TransportLayerAddress	OPTIONAL,
	transportFormatManagement	TransportFormatManagement,
	iE-Extensions			ProtocolExtensionContainer { {DSCHInformationItem-RL-SetupRspTDD-ExtIEs} } OPTIONAL,
	...
}

DSCHInformationItem-RL-SetupRspTDD-ExtIEs RNSAP-PROTOCOL-EXTENSION ::= {
	...
}

USCH-InformationResponse-RL-SetupRspTDD ::= ProtocolIE-Single-Container {{USCH-InformationList-RL-SetupRspTDD}}

USCH-InformationList-RL-SetupRspTDD RNSAP-PROTOCOL-IES ::= {
	{ ID id-USCH-InformationListIEs-RL-SetupRspTDD		CRITICALITY ignore	TYPE USCH-InformationListIEs-RL-SetupRspTDD PRESENCE mandatory }
}

USCH-InformationListIEs-RL-SetupRspTDD ::= SEQUENCE (SIZE(0..maxNoOfUSCHs)) OF USCHInformationItem-RL-SetupRspTDD

USCHInformationItem-RL-SetupRspTDD ::= SEQUENCE {
	usch-ID						USCH-ID,
	bindingID					BindingID	OPTIONAL,
	transportLayerAddress		TransportLayerAddress	OPTIONAL,
	transportFormatManagement	TransportFormatManagement,
	iE-Extensions				ProtocolExtensionContainer { {USCHInformationItem-RL-SetupRspTDD-ExtIEs} } OPTIONAL,
	...
}

USCHInformationItem-RL-SetupRspTDD-ExtIEs RNSAP-PROTOCOL-EXTENSION ::= {
	...
}

RadioLinkSetupResponseTDD-Extensions RNSAP-PROTOCOL-EXTENSION ::= {
	{ ID id-RL-LCR-InformationResponse-RL-SetupRspTDD	CRITICALITY ignore	EXTENSION 	RL-LCR-InformationResponse-RL-SetupRspTDD		PRESENCE optional}|
	--Mandatory for 1.28Mcps TDD only
	{ ID id-HSDSCH-RNTI									CRITICALITY ignore	EXTENSION HSDSCH-RNTI												PRESENCE optional }|
	{ ID id-HSDSCH-TDD-Information-Response				CRITICALITY ignore	EXTENSION HSDSCH-TDD-Information-Response					PRESENCE optional }|
	{ ID id-DSCH-RNTI									CRITICALITY ignore	EXTENSION DSCH-RNTI													PRESENCE optional }|
	{ ID id-Active-MBMS-Bearer-ServiceTDD-PFL			CRITICALITY	ignore	EXTENSION Active-MBMS-Bearer-Service-ListTDD-PFL			PRESENCE optional }|
	{ ID id-RL-InformationResponse-RL-SetupRspTDD768	CRITICALITY ignore	EXTENSION RL-InformationResponse-RL-SetupRspTDD768		PRESENCE optional }|
	{ ID id-E-DCH-Information-Response					CRITICALITY ignore	EXTENSION E-DCH-Information-Response						PRESENCE optional	}|
	{ ID id-E-DCH-768-Information-Response				CRITICALITY ignore	EXTENSION E-DCH-768-Information-Response					PRESENCE optional	}|
	{ ID id-E-DCH-LCR-Information-Response				CRITICALITY ignore	EXTENSION E-DCH-LCR-Information-Response					PRESENCE optional	}|
	{ ID id-ContinuousPacketConnectivity-DRX-Information-ResponseLCR	CRITICALITY ignore	EXTENSION ContinuousPacketConnectivity-DRX-Information-ResponseLCR			PRESENCE optional	}|
	{ ID id-HS-DSCH-Semi-PersistentScheduling-Information-ResponseLCR	CRITICALITY ignore	EXTENSION HS-DSCH-Semi-PersistentScheduling-Information-ResponseLCR			PRESENCE optional	}|
	{ ID id-E-DCH-Semi-PersistentScheduling-Information-ResponseLCR		CRITICALITY ignore	EXTENSION E-DCH-Semi-PersistentScheduling-Information-ResponseLCR			PRESENCE optional}|
	{ ID id-E-RNTI-For-FACH								CRITICALITY ignore	EXTENSION E-RNTI													PRESENCE optional }|
	{ ID id-H-RNTI-For-FACH								CRITICALITY ignore	EXTENSION HSDSCH-RNTI												PRESENCE optional }|
	{ ID id-DCH-MeasurementOccasion-Information			CRITICALITY reject	EXTENSION DCH-MeasurementOccasion-Information				PRESENCE optional},
	...
}

RL-LCR-InformationResponse-RL-SetupRspTDD ::= SEQUENCE {
	rL-ID						RL-ID,
	uRA-Information				URA-Information,
	sAI							SAI,
	gA-Cell						GA-Cell		OPTIONAL,
	gA-AccessPointPosition		GA-AccessPointPosition	OPTIONAL,
	ul-TimeSlot-ISCP-LCR-Info	UL-TimeSlot-ISCP-LCR-Info,
	maxUL-SIR					UL-SIR,
	minUL-SIR					UL-SIR,
	maximumAllowedULTxPower		MaximumAllowedULTxPower,
	maximumDLTxPower			DL-Power,
	minimumDLTxPower			DL-Power,
	uARFCNforNt					UARFCN					OPTIONAL,
	cellParameterID				CellParameterID			OPTIONAL,
	sCTD-Indicator		SCTD-Indicator	OPTIONAL,
	pCCPCH-Power				PCCPCH-Power,
	alphaValue					AlphaValue,
	ul-PhysCH-SF-Variation		UL-PhysCH-SF-Variation,
	synchronisationConfiguration			SynchronisationConfiguration,
	secondary-LCR-CCPCH-Info-TDD			Secondary-LCR-CCPCH-Info-TDD					OPTIONAL,
	ul-LCR-CCTrCHInformation				UL-LCR-CCTrCHInformationList-RL-SetupRspTDD		OPTIONAL,
	dl-LCR-CCTrCHInformation				DL-LCR-CCTrCHInformationList-RL-SetupRspTDD		OPTIONAL,
	dCH-InformationResponse					DCH-InformationResponseList-RL-SetupRspTDD	OPTIONAL,
	dsch-LCR-InformationResponse			DSCH-LCR-InformationResponse-RL-SetupRspTDD		OPTIONAL,
	usch-LCR-InformationResponse			USCH-LCR-InformationResponse-RL-SetupRspTDD     OPTIONAL,
	neighbouring-UMTS-CellInformation		Neighbouring-UMTS-CellInformation               OPTIONAL,
	neighbouring-GSM-CellInformation		Neighbouring-GSM-CellInformation				OPTIONAL,
	iE-Extensions							ProtocolExtensionContainer { { RL-LCR-InformationResponseList-RL-SetupRspTDD-ExtIEs} }		OPTIONAL,
	...
}

RL-LCR-InformationResponseList-RL-SetupRspTDD-ExtIEs RNSAP-PROTOCOL-EXTENSION ::= {
	{ ID id-GA-CellAdditionalShapes					CRITICALITY	ignore	EXTENSION	GA-CellAdditionalShapes				PRESENCE optional }|
	{ ID id-HCS-Prio								CRITICALITY	ignore	EXTENSION	HCS-Prio									PRESENCE optional }|
	{ ID id-UL-TimingAdvanceCtrl-LCR				CRITICALITY ignore	EXTENSION	UL-TimingAdvanceCtrl-LCR				PRESENCE optional }|
	--Mandatory for 1.28Mcps TDD only
	{ ID id-PowerControlGAP							CRITICALITY ignore	EXTENSION	ControlGAP				PRESENCE optional }|
	-- Applicable to 1.28Mcps TDD only
	{ ID id-SixtyfourQAM-DL-SupportIndicator		CRITICALITY ignore	EXTENSION	SixtyfourQAM-DL-SupportIndicator	PRESENCE optional }|
	-- Applicable to 1.28Mcps TDD only
	{ ID id-Neighbouring-E-UTRA-CellInformation		CRITICALITY ignore	EXTENSION Neighbouring-E-UTRA-CellInformation	PRESENCE optional }|
	{ ID id-IdleIntervalInformation					CRITICALITY ignore	EXTENSION	IdleIntervalInformation			PRESENCE optional },
	...
}

UL-LCR-CCTrCHInformationList-RL-SetupRspTDD ::= ProtocolIE-Single-Container {{UL-LCR-CCTrCHInformationListIEs-RL-SetupRspTDD}}

UL-LCR-CCTrCHInformationListIEs-RL-SetupRspTDD RNSAP-PROTOCOL-IES ::= {
	{ ID id-UL-CCTrCH-LCR-InformationListIE-RL-SetupRspTDD   CRITICALITY ignore	TYPE UL-LCR-CCTrCHInformationListIE-RL-SetupRspTDD		PRESENCE mandatory }
}

UL-LCR-CCTrCHInformationListIE-RL-SetupRspTDD ::= SEQUENCE (SIZE (1..maxNrOfCCTrCHsLCR)) OF UL-LCR-CCTrCHInformationItem-RL-SetupRspTDD

UL-LCR-CCTrCHInformationItem-RL-SetupRspTDD ::= SEQUENCE {
	cCTrCH-ID					CCTrCH-ID,
	ul-DPCH-LCR-Information		UL-DPCH-LCR-InformationList-RL-SetupRspTDD		OPTIONAL,
	iE-Extensions				ProtocolExtensionContainer { {UL-LCR-CCTrCHInformationItem-RL-SetupRspTDD-ExtIEs} } OPTIONAL,
	...
}

UL-LCR-CCTrCHInformationItem-RL-SetupRspTDD-ExtIEs RNSAP-PROTOCOL-EXTENSION ::= {
	{ID id-UL-SIR-Target-CCTrCH-LCR-InformationItem-RL-SetupRspTDD		CRITICALITY ignore		EXTENSION UL-SIR		PRESENCE optional},
	...
}

UL-DPCH-LCR-InformationList-RL-SetupRspTDD ::= ProtocolIE-Single-Container { {UL-DPCH-LCR-InformationListIEs-RL-SetupRspTDD} }

UL-DPCH-LCR-InformationListIEs-RL-SetupRspTDD RNSAP-PROTOCOL-IES ::= {
	{ ID id-UL-DPCH-LCR-InformationItem-RL-SetupRspTDD		CRITICALITY ignore	TYPE UL-DPCH-LCR-InformationItem-RL-SetupRspTDD  PRESENCE mandatory	}
}

UL-DPCH-LCR-InformationItem-RL-SetupRspTDD ::= SEQUENCE {
	repetitionPeriod				RepetitionPeriod,
	repetitionLength				RepetitionLength,
	tDD-DPCHOffset					TDD-DPCHOffset,
	uL-TimeslotLCR-Information		UL-TimeslotLCR-Information,
	iE-Extensions					ProtocolExtensionContainer { {UL-DPCH-LCR-InformationItem-RL-SetupRspTDD-ExtIEs} } OPTIONAL,
	...
}

UL-DPCH-LCR-InformationItem-RL-SetupRspTDD-ExtIEs RNSAP-PROTOCOL-EXTENSION ::= {
	...
}
DL-LCR-CCTrCHInformationList-RL-SetupRspTDD ::= ProtocolIE-Single-Container {{DL-LCR-CCTrCHInformationListIEs-RL-SetupRspTDD}}

DL-LCR-CCTrCHInformationListIEs-RL-SetupRspTDD RNSAP-PROTOCOL-IES ::= {
	{ ID id-DL-CCTrCH-LCR-InformationListIE-RL-SetupRspTDD   CRITICALITY ignore	TYPE DL-CCTrCH-LCR-InformationListIE-RL-SetupRspTDD  PRESENCE mandatory }
}

DL-CCTrCH-LCR-InformationListIE-RL-SetupRspTDD ::= SEQUENCE (SIZE (1..maxNrOfCCTrCHsLCR)) OF DL-CCTrCH-LCR-InformationItem-RL-SetupRspTDD

DL-CCTrCH-LCR-InformationItem-RL-SetupRspTDD ::= SEQUENCE {
	cCTrCH-ID					CCTrCH-ID,
	dl-DPCH-LCR-Information		DL-DPCH-LCR-InformationList-RL-SetupRspTDD		OPTIONAL,
	iE-Extensions				ProtocolExtensionContainer { {DL-CCTrCH-LCR-InformationItem-RL-SetupRspTDD-ExtIEs} } OPTIONAL,
	...
}

DL-CCTrCH-LCR-InformationItem-RL-SetupRspTDD-ExtIEs RNSAP-PROTOCOL-EXTENSION ::= {
	...
}

DL-DPCH-LCR-InformationList-RL-SetupRspTDD ::= ProtocolIE-Single-Container { {DL-DPCH-LCR-InformationListIEs-RL-SetupRspTDD} }

DL-DPCH-LCR-InformationListIEs-RL-SetupRspTDD RNSAP-PROTOCOL-IES ::= {
	{ ID id-DL-DPCH-LCR-InformationItem-RL-SetupRspTDD		CRITICALITY ignore	TYPE DL-DPCH-LCR-InformationItem-RL-SetupRspTDD  PRESENCE mandatory	}
}

DL-DPCH-LCR-InformationItem-RL-SetupRspTDD ::= SEQUENCE {
	repetitionPeriod				RepetitionPeriod,
	repetitionLength				RepetitionLength,
	tDD-DPCHOffset					TDD-DPCHOffset,
	dL-Timeslot-LCR-Information		DL-TimeslotLCR-Information,
	tSTD-Indicator					TSTD-Indicator,
	iE-Extensions					ProtocolExtensionContainer { {DL-DPCH-LCR-InformationItem-RL-SetupRspTDD-ExtIEs} } OPTIONAL,
	...
}

DL-DPCH-LCR-InformationItem-RL-SetupRspTDD-ExtIEs RNSAP-PROTOCOL-EXTENSION ::= {
	...
}

DSCH-LCR-InformationResponse-RL-SetupRspTDD ::= ProtocolIE-Single-Container {{DSCH-LCR-InformationList-RL-SetupRspTDD}}

DSCH-LCR-InformationList-RL-SetupRspTDD RNSAP-PROTOCOL-IES ::= {
	{ ID id-DSCH-LCR-InformationListIEs-RL-SetupRspTDD		CRITICALITY ignore	TYPE DSCH-LCR-InformationListIEs-RL-SetupRspTDD PRESENCE mandatory }
}

DSCH-LCR-InformationListIEs-RL-SetupRspTDD ::= SEQUENCE (SIZE(0..maxNoOfDSCHsLCR)) OF DSCH-LCR-InformationItem-RL-SetupRspTDD

DSCH-LCR-InformationItem-RL-SetupRspTDD ::= SEQUENCE {
	dsch-ID								DSCH-ID,
	dSCH-FlowControlInformation			DSCH-FlowControlInformation,
	bindingID							BindingID	OPTIONAL,
	transportLayerAddress				TransportLayerAddress	OPTIONAL,
	transportFormatManagement			TransportFormatManagement,
	iE-Extensions						ProtocolExtensionContainer { {DSCH-LCR-InformationItem-RL-SetupRspTDD-ExtIEs} } OPTIONAL,
	...
}

DSCH-LCR-InformationItem-RL-SetupRspTDD-ExtIEs RNSAP-PROTOCOL-EXTENSION ::= {
	...
}

USCH-LCR-InformationResponse-RL-SetupRspTDD ::= ProtocolIE-Single-Container {{USCH-LCR-InformationList-RL-SetupRspTDD}}

USCH-LCR-InformationList-RL-SetupRspTDD RNSAP-PROTOCOL-IES ::= {
	{ ID id-USCH-LCR-InformationListIEs-RL-SetupRspTDD		CRITICALITY ignore	TYPE USCH-LCR-InformationListIEs-RL-SetupRspTDD PRESENCE mandatory }
}

USCH-LCR-InformationListIEs-RL-SetupRspTDD ::= SEQUENCE (SIZE(0..maxNoOfUSCHsLCR)) OF USCH-LCR-InformationItem-RL-SetupRspTDD

USCH-LCR-InformationItem-RL-SetupRspTDD ::= SEQUENCE {
	usch-ID						USCH-ID,
	bindingID					BindingID	OPTIONAL,
	transportLayerAddress		TransportLayerAddress	OPTIONAL,
	transportFormatManagement	TransportFormatManagement,
	iE-Extensions				ProtocolExtensionContainer { {USCH-LCR-InformationItem-RL-SetupRspTDD-ExtIEs} } OPTIONAL,
	...
}

USCH-LCR-InformationItem-RL-SetupRspTDD-ExtIEs RNSAP-PROTOCOL-EXTENSION ::= {
	...
}

RL-InformationResponse-RL-SetupRspTDD768 ::= SEQUENCE {
	rL-ID						RL-ID,
	uRA-Information				URA-Information		OPTIONAL,
	sAI							SAI,
	gA-Cell						GA-Cell		OPTIONAL,
	gA-AccessPointPosition		GA-AccessPointPosition	OPTIONAL,
	ul-TimeSlot-ISCP-Info		UL-TimeSlot-ISCP-Info,
	maxUL-SIR					UL-SIR,
	minUL-SIR					UL-SIR,
	maximumAllowedULTxPower		MaximumAllowedULTxPower,
	maximumDLTxPower			DL-Power,
	minimumDLTxPower			DL-Power,
	uARFCNforNt					UARFCN				OPTIONAL,
	cellParameterID				CellParameterID		OPTIONAL,
	syncCase					SyncCase			OPTIONAL,
	sCH-TimeSlot				SCH-TimeSlot		OPTIONAL,
	-- This IE shall be present if Sync Case IE is equal to "Case2". --
	sCTD-Indicator				SCTD-Indicator	OPTIONAL,
	pCCPCH-Power				PCCPCH-Power,
	timingAdvanceApplied		TimingAdvanceApplied,
	alphaValue					AlphaValue,
	ul-PhysCH-SF-Variation		UL-PhysCH-SF-Variation,
	synchronisationConfiguration		SynchronisationConfiguration,
	secondary-CCPCH-Info-TDD768			Secondary-CCPCH-Info-TDD768		OPTIONAL,
	ul-CCTrCHInformation768				UL-CCTrCHInformationList-RL-SetupRspTDD768		OPTIONAL,
	dl-CCTrCHInformation768				DL-CCTrCHInformationList-RL-SetupRspTDD768		OPTIONAL,
	dCH-InformationResponse				DCH-InformationResponseList-RL-SetupRspTDD	OPTIONAL,
	dsch-InformationResponse			DSCH-InformationResponse-RL-SetupRspTDD OPTIONAL,
	usch-InformationResponse			USCH-InformationResponse-RL-SetupRspTDD OPTIONAL,
	neighbouring-UMTS-CellInformation			Neighbouring-UMTS-CellInformation OPTIONAL,
	neighbouring-GSM-CellInformation			Neighbouring-GSM-CellInformation OPTIONAL,
	gA-CellAdditionalShapes						GA-CellAdditionalShapes		OPTIONAL,
	hCS-Prio							HCS-Prio		OPTIONAL,
	timeSlot-RL-SetupRspTDD				TimeSlot	OPTIONAL,
	-- This IE shall be present if Sync Case IE is Case1. --

	iE-Extensions					ProtocolExtensionContainer { {RL-InformationResponse-RL-SetupRspTDD768-ExtIEs} } OPTIONAL,
	...
}

RL-InformationResponse-RL-SetupRspTDD768-ExtIEs RNSAP-PROTOCOL-EXTENSION ::= {
	{ ID id-Neighbouring-E-UTRA-CellInformation			CRITICALITY ignore	EXTENSION Neighbouring-E-UTRA-CellInformation				PRESENCE optional },
	...
}

UL-CCTrCHInformationList-RL-SetupRspTDD768 ::= ProtocolIE-Single-Container {{UL-CCTrCHInformationListIEs-RL-SetupRspTDD768}}

UL-CCTrCHInformationListIEs-RL-SetupRspTDD768 RNSAP-PROTOCOL-IES ::= {
	{ ID id-UL-CCTrCH-InformationListIE-RL-SetupRspTDD768   CRITICALITY ignore	TYPE UL-CCTrCHInformationListIE-RL-SetupRspTDD768		PRESENCE mandatory }
}

UL-CCTrCHInformationListIE-RL-SetupRspTDD768 ::= SEQUENCE (SIZE (1..maxNrOfCCTrCHs)) OF UL-CCTrCHInformationItem-RL-SetupRspTDD768

UL-CCTrCHInformationItem-RL-SetupRspTDD768 ::= SEQUENCE {
	cCTrCH-ID					CCTrCH-ID,
	ul-DPCH-Information768				UL-DPCH-InformationList-RL-SetupRspTDD768		OPTIONAL,
	uL-SIR-Target-CCTrCH-InformationItem-RL-SetupRspTDD768		UL-SIR		OPTIONAL,
	iE-Extensions					ProtocolExtensionContainer { {UL-CCTrCHInformationItem-RL-SetupRspTDD768-ExtIEs} } OPTIONAL,
	...
}

UL-CCTrCHInformationItem-RL-SetupRspTDD768-ExtIEs RNSAP-PROTOCOL-EXTENSION ::= {
	...
}

UL-DPCH-InformationList-RL-SetupRspTDD768 ::= ProtocolIE-Single-Container { {UL-DPCH-InformationListIEs-RL-SetupRspTDD768} }

UL-DPCH-InformationListIEs-RL-SetupRspTDD768 RNSAP-PROTOCOL-IES ::= {
	{ ID id-UL-DPCH-InformationItem-RL-SetupRspTDD768		CRITICALITY ignore	TYPE UL-DPCH-InformationItem-RL-SetupRspTDD768  PRESENCE mandatory	}
}

UL-DPCH-InformationItem-RL-SetupRspTDD768 ::= SEQUENCE {
	repetitionPeriod				RepetitionPeriod,
	repetitionLength				RepetitionLength,
	tDD-DPCHOffset					TDD-DPCHOffset,
	uL-Timeslot-Information768			UL-Timeslot-Information768,
	iE-Extensions					ProtocolExtensionContainer { {UL-DPCH-InformationItem-RL-SetupRspTDD768-ExtIEs} } OPTIONAL,
	...
}

UL-DPCH-InformationItem-RL-SetupRspTDD768-ExtIEs RNSAP-PROTOCOL-EXTENSION ::= {
	...
}

DL-CCTrCHInformationList-RL-SetupRspTDD768 ::= ProtocolIE-Single-Container {{DL-CCTrCHInformationListIEs-RL-SetupRspTDD768}}

DL-CCTrCHInformationListIEs-RL-SetupRspTDD768 RNSAP-PROTOCOL-IES ::= {
	{ ID id-DL-CCTrCH-InformationListIE-RL-SetupRspTDD768   CRITICALITY ignore	TYPE DL-CCTrCHInformationListIE-RL-SetupRspTDD768  PRESENCE mandatory }
}

DL-CCTrCHInformationListIE-RL-SetupRspTDD768 ::= SEQUENCE (SIZE (1..maxNrOfCCTrCHs)) OF DL-CCTrCHInformationItem-RL-SetupRspTDD768

DL-CCTrCHInformationItem-RL-SetupRspTDD768 ::= SEQUENCE {
	cCTrCH-ID					CCTrCH-ID,
	dl-DPCH-Information768				DL-DPCH-InformationList-RL-SetupRspTDD768		OPTIONAL,
	cCTrCH-Maximum-DL-Power				DL-Power		OPTIONAL, -- this is a DCH type CCTrCH power
	cCTrCH-Minimum-DL-Power				DL-Power		OPTIONAL, -- this is a DCH type CCTrCH power
	iE-Extensions					ProtocolExtensionContainer { {DL-CCTrCHInformationItem-RL-SetupRspTDD768-ExtIEs} } OPTIONAL,
	...
}

DL-CCTrCHInformationItem-RL-SetupRspTDD768-ExtIEs RNSAP-PROTOCOL-EXTENSION ::= {
	...
}

DL-DPCH-InformationList-RL-SetupRspTDD768 ::= ProtocolIE-Single-Container { {DL-DPCH-InformationListIEs-RL-SetupRspTDD768} }

DL-DPCH-InformationListIEs-RL-SetupRspTDD768 RNSAP-PROTOCOL-IES ::= {
	{ ID id-DL-DPCH-InformationItem-RL-SetupRspTDD768		CRITICALITY ignore	TYPE DL-DPCH-InformationItem-RL-SetupRspTDD768  PRESENCE mandatory	}
}

DL-DPCH-InformationItem-RL-SetupRspTDD768 ::= SEQUENCE {
	repetitionPeriod				RepetitionPeriod,
	repetitionLength				RepetitionLength,
	tDD-DPCHOffset					TDD-DPCHOffset,
	dL-Timeslot-Information768		DL-Timeslot-Information768,
	iE-Extensions					ProtocolExtensionContainer { {DL-DPCH-InformationItem-RL-SetupRspTDD768-ExtIEs} } OPTIONAL,
	...
}

DL-DPCH-InformationItem-RL-SetupRspTDD768-ExtIEs RNSAP-PROTOCOL-EXTENSION ::= {
	...
}

-- **************************************************************
--
-- RADIO LINK SETUP FAILURE FDD
--
-- **************************************************************

RadioLinkSetupFailureFDD ::= SEQUENCE {
	protocolIEs                     ProtocolIE-Container       {{RadioLinkSetupFailureFDD-IEs}},
	protocolExtensions              ProtocolExtensionContainer {{RadioLinkSetupFailureFDD-Extensions}}                   OPTIONAL,
	...
}

RadioLinkSetupFailureFDD-IEs RNSAP-PROTOCOL-IES ::= {
	{ ID id-D-RNTI	CRITICALITY ignore	TYPE D-RNTI	PRESENCE optional	} |
	{ ID id-CN-PS-DomainIdentifier	CRITICALITY ignore	TYPE CN-PS-DomainIdentifier	PRESENCE optional	} |
	{ ID id-CN-CS-DomainIdentifier	CRITICALITY ignore	TYPE CN-CS-DomainIdentifier	PRESENCE optional	} |
	{ ID id-CauseLevel-RL-SetupFailureFDD	CRITICALITY ignore	TYPE CauseLevel-RL-SetupFailureFDD	PRESENCE mandatory }|
	{ ID id-UL-SIRTarget	CRITICALITY ignore	TYPE UL-SIR 	PRESENCE optional	} |
	{ ID id-CriticalityDiagnostics	CRITICALITY ignore	TYPE CriticalityDiagnostics	PRESENCE optional	},
	...
}

CauseLevel-RL-SetupFailureFDD ::= CHOICE {
	generalCause		GeneralCauseList-RL-SetupFailureFDD,
	rLSpecificCause		RLSpecificCauseList-RL-SetupFailureFDD,
	...
}

GeneralCauseList-RL-SetupFailureFDD ::= SEQUENCE {
	cause										Cause,
	iE-Extensions								ProtocolExtensionContainer { { GeneralCauseItem-RL-SetupFailureFDD-ExtIEs} }		OPTIONAL,
	...
}

GeneralCauseItem-RL-SetupFailureFDD-ExtIEs RNSAP-PROTOCOL-EXTENSION ::= {
	...
}

RLSpecificCauseList-RL-SetupFailureFDD ::= SEQUENCE {
	unsuccessful-RL-InformationRespList-RL-SetupFailureFDD		UnsuccessfulRL-InformationResponseList-RL-SetupFailureFDD,
	successful-RL-InformationRespList-RL-SetupFailureFDD		SuccessfulRL-InformationResponseList-RL-SetupFailureFDD	OPTIONAL,
	iE-Extensions								ProtocolExtensionContainer { { RLSpecificCauseItem-RL-SetupFailureFDD-ExtIEs} }		OPTIONAL,
	...
}

RLSpecificCauseItem-RL-SetupFailureFDD-ExtIEs RNSAP-PROTOCOL-EXTENSION ::= {
	{ ID id-HSDSCH-RNTI							CRITICALITY ignore		EXTENSION HSDSCH-RNTI									PRESENCE optional }|
	{ ID id-HSDSCH-FDD-Information-Response		CRITICALITY ignore		EXTENSION HSDSCH-FDD-Information-Response		PRESENCE optional }|
	{ ID id-Continuous-Packet-Connectivity-HS-SCCH-Less-Information-Response		CRITICALITY ignore		EXTENSION Continuous-Packet-Connectivity-HS-SCCH-Less-Information-Response		PRESENCE optional }|
	{ ID id-SixtyfourQAM-DL-SupportIndicator	CRITICALITY ignore		EXTENSION SixtyfourQAM-DL-SupportIndicator		PRESENCE optional }|
	{ ID id-Additional-HS-Cell-Information-Response	CRITICALITY ignore		EXTENSION Additional-HS-Cell-Information-Response-List		PRESENCE optional }|
	{ ID id-Additional-EDCH-Cell-Information-Response		CRITICALITY ignore	EXTENSION	Additional-EDCH-Cell-Information-Response-List			PRESENCE optional},
	...
}

UnsuccessfulRL-InformationResponseList-RL-SetupFailureFDD ::= SEQUENCE (SIZE (1..maxNrOfRLs)) OF ProtocolIE-Single-Container { {UnsuccessfulRL-InformationResponse-RL-SetupFailureFDD-IEs} }

UnsuccessfulRL-InformationResponse-RL-SetupFailureFDD-IEs RNSAP-PROTOCOL-IES ::= {
	{ ID id-UnsuccessfulRL-InformationResponse-RL-SetupFailureFDD		CRITICALITY ignore	TYPE UnsuccessfulRL-InformationResponse-RL-SetupFailureFDD		PRESENCE mandatory	}
}

UnsuccessfulRL-InformationResponse-RL-SetupFailureFDD ::= SEQUENCE {
	rL-ID						RL-ID,
	cause						Cause,
	iE-Extensions					ProtocolExtensionContainer { {UnsuccessfulRL-InformationResponse-RL-SetupFailureFDD-ExtIEs} } OPTIONAL,
	...
}

UnsuccessfulRL-InformationResponse-RL-SetupFailureFDD-ExtIEs RNSAP-PROTOCOL-EXTENSION ::= {
	{ ID id-Max-UE-DTX-Cycle		CRITICALITY ignore		EXTENSION Max-UE-DTX-Cycle				PRESENCE conditional },
	-- This IE shall be present if the Cause IE is set to "Continuous Packet Connectivity UE DTX Cycle not Available".
	...
}

SuccessfulRL-InformationResponseList-RL-SetupFailureFDD ::= SEQUENCE (SIZE (0..maxNrOfRLs-1)) OF ProtocolIE-Single-Container { {SuccessfulRL-InformationResponse-RL-SetupFailureFDD-IEs} }

SuccessfulRL-InformationResponse-RL-SetupFailureFDD-IEs RNSAP-PROTOCOL-IES ::= {
	{ ID id-SuccessfulRL-InformationResponse-RL-SetupFailureFDD		CRITICALITY ignore	TYPE SuccessfulRL-InformationResponse-RL-SetupFailureFDD		PRESENCE mandatory	}
}

SuccessfulRL-InformationResponse-RL-SetupFailureFDD ::= SEQUENCE {
	rL-ID									RL-ID,
	rL-Set-ID								RL-Set-ID,
	uRA-Information							URA-Information						OPTIONAL,
	sAI										SAI,
	gA-Cell									GA-Cell		OPTIONAL,
	gA-AccessPointPosition					GA-AccessPointPosition				OPTIONAL,
	received-total-wide-band-power			Received-total-wide-band-power,
	not-Used-secondary-CCPCH-Info					NULL				OPTIONAL,
	dl-CodeInformation						FDD-DL-CodeInformation,
	diversityIndication						DiversityIndication-RL-SetupFailureFDD,
	sSDT-SupportIndicator					SSDT-SupportIndicator,
	maxUL-SIR								UL-SIR,
	minUL-SIR								UL-SIR,
	closedlooptimingadjustmentmode			Closedlooptimingadjustmentmode		OPTIONAL,
	maximumAllowedULTxPower					MaximumAllowedULTxPower,
	maximumDLTxPower						DL-Power,
	minimumDLTxPower						DL-Power,
	primaryCPICH-Power						PrimaryCPICH-Power,
	primaryScramblingCode					PrimaryScramblingCode				OPTIONAL,
	uL-UARFCN								UARFCN								OPTIONAL,
	dL-UARFCN								UARFCN								OPTIONAL,
	not-Used-dSCH-InformationResponse-RL-SetupFailureFDD	NULL				OPTIONAL,
	neighbouring-UMTS-CellInformation		Neighbouring-UMTS-CellInformation	OPTIONAL,
	neighbouring-GSM-CellInformation		Neighbouring-GSM-CellInformation	OPTIONAL,
	pC-Preamble								PC-Preamble,
	sRB-Delay								SRB-Delay,
	iE-Extensions							ProtocolExtensionContainer { {SuccessfulRL-InformationResponse-RL-SetupFailureFDD-ExtIEs} } OPTIONAL,
	...
}

SuccessfulRL-InformationResponse-RL-SetupFailureFDD-ExtIEs RNSAP-PROTOCOL-EXTENSION ::= {
	{ ID id-GA-CellAdditionalShapes						CRITICALITY ignore	EXTENSION GA-CellAdditionalShapes								PRESENCE optional }|
	{ ID id-DL-PowerBalancing-ActivationIndicator		CRITICALITY ignore	EXTENSION DL-PowerBalancing-ActivationIndicator			PRESENCE optional }|
	{ ID id-HCS-Prio									CRITICALITY ignore	EXTENSION HCS-Prio													PRESENCE optional }|
	{ ID id-Primary-CPICH-Usage-For-Channel-Estimation	CRITICALITY ignore	EXTENSION Primary-CPICH-Usage-For-Channel-Estimation	PRESENCE optional }|
	{ ID id-Secondary-CPICH-Information					CRITICALITY ignore	EXTENSION Secondary-CPICH-Information						PRESENCE optional }|
	{ ID id-Active-MBMS-Bearer-ServiceFDD-PFL			CRITICALITY ignore	EXTENSION Active-MBMS-Bearer-Service-ListFDD-PFL			PRESENCE optional }|
	{ ID id-EDCH-RLSet-Id								CRITICALITY ignore	EXTENSION RL-Set-ID													PRESENCE optional }|
	{ ID id-EDCH-FDD-DL-ControlChannelInformation		CRITICALITY ignore	EXTENSION EDCH-FDD-DL-ControlChannelInformation			PRESENCE optional }|
	{ ID id-Initial-DL-DPCH-TimingAdjustment			CRITICALITY ignore	EXTENSION DL-DPCH-TimingAdjustment							PRESENCE optional }|
	{ ID id-Neighbouring-E-UTRA-CellInformation			CRITICALITY ignore	EXTENSION Neighbouring-E-UTRA-CellInformation				PRESENCE optional }|
	{ ID id-HSDSCH-PreconfigurationInfo					CRITICALITY ignore	EXTENSION HSDSCH-PreconfigurationInfo						PRESENCE optional }|
	{ ID id-F-DPCH-SlotFormat							CRITICALITY ignore	EXTENSION F-DPCH-SlotFormat										PRESENCE optional }|
	{ ID id-Non-Serving-RL-Preconfig-Info				CRITICALITY ignore	EXTENSION Non-Serving-RL-Preconfig-Info						PRESENCE optional },
	...
}

DiversityIndication-RL-SetupFailureFDD ::= CHOICE {
	combining						Combining-RL-SetupFailureFDD,
	nonCombiningOrFirstRL		NonCombiningOrFirstRL-RL-SetupFailureFDD
}

Combining-RL-SetupFailureFDD ::= SEQUENCE {
	rL-ID						RL-ID,
	iE-Extensions				ProtocolExtensionContainer { { CombiningItem-RL-SetupFailureFDD-ExtIEs} } OPTIONAL,
	...
}

CombiningItem-RL-SetupFailureFDD-ExtIEs RNSAP-PROTOCOL-EXTENSION ::= {
	{ ID id-DCH-InformationResponse			CRITICALITY ignore	EXTENSION DCH-InformationResponse			PRESENCE optional	}|
	{ ID id-EDCH-FDD-InformationResponse	CRITICALITY ignore	EXTENSION EDCH-FDD-InformationResponse			PRESENCE optional	},
	...
}

NonCombiningOrFirstRL-RL-SetupFailureFDD ::= SEQUENCE {
	dCH-InformationResponse					DCH-InformationResponse,
	iE-Extensions							ProtocolExtensionContainer { { NonCombiningOrFirstRLItem-RL-SetupFailureFDD-ExtIEs} } OPTIONAL,
	...
}

NonCombiningOrFirstRLItem-RL-SetupFailureFDD-ExtIEs RNSAP-PROTOCOL-EXTENSION ::= {
	{ ID id-EDCH-FDD-InformationResponse	CRITICALITY ignore	EXTENSION EDCH-FDD-InformationResponse			PRESENCE optional	},
	...
}

RadioLinkSetupFailureFDD-Extensions RNSAP-PROTOCOL-EXTENSION ::= {
	...
}

-- **************************************************************
--
-- RADIO LINK SETUP FAILURE TDD
--
-- **************************************************************

RadioLinkSetupFailureTDD ::= SEQUENCE {
	protocolIEs                     ProtocolIE-Container       {{RadioLinkSetupFailureTDD-IEs}},
	protocolExtensions              ProtocolExtensionContainer {{RadioLinkSetupFailureTDD-Extensions}}                   OPTIONAL,
	...
}

RadioLinkSetupFailureTDD-IEs RNSAP-PROTOCOL-IES ::= {
	{ ID id-CauseLevel-RL-SetupFailureTDD	CRITICALITY ignore	TYPE CauseLevel-RL-SetupFailureTDD		PRESENCE mandatory }|
	{ ID id-CriticalityDiagnostics			CRITICALITY ignore	TYPE CriticalityDiagnostics					PRESENCE optional	},
	...
}

CauseLevel-RL-SetupFailureTDD ::= CHOICE {
	generalCause		GeneralCauseList-RL-SetupFailureTDD,
	rLSpecificCause		RLSpecificCauseList-RL-SetupFailureTDD,
	...
}

GeneralCauseList-RL-SetupFailureTDD ::= SEQUENCE {
	cause						Cause,
	iE-Extensions				ProtocolExtensionContainer { { GeneralCauseItem-RL-SetupFailureTDD-ExtIEs} }		OPTIONAL,
	...
}

GeneralCauseItem-RL-SetupFailureTDD-ExtIEs RNSAP-PROTOCOL-EXTENSION ::= {
	...
}

RLSpecificCauseList-RL-SetupFailureTDD ::= SEQUENCE {
	unsuccessful-RL-InformationRespItem-RL-SetupFailureTDD	Unsuccessful-RL-InformationRespItem-RL-SetupFailureTDD,
	iE-Extensions											ProtocolExtensionContainer { { RLSpecificCauseItem-RL-SetupFailureTDD-ExtIEs} }		OPTIONAL,
	...
}

RLSpecificCauseItem-RL-SetupFailureTDD-ExtIEs RNSAP-PROTOCOL-EXTENSION ::= {
	{ ID id-SixtyfourQAM-DL-SupportIndicator	CRITICALITY ignore		EXTENSION SixtyfourQAM-DL-SupportIndicator		PRESENCE optional },
	...
}

Unsuccessful-RL-InformationRespItem-RL-SetupFailureTDD ::= ProtocolIE-Single-Container { {Unsuccessful-RL-InformationRespItemIE-RL-SetupFailureTDD} }

Unsuccessful-RL-InformationRespItemIE-RL-SetupFailureTDD RNSAP-PROTOCOL-IES ::= {
	{ ID	id-UnsuccessfulRL-InformationResponse-RL-SetupFailureTDD		CRITICALITY	ignore 		TYPE 	UnsuccessfulRL-InformationResponse-RL-SetupFailureTDD		PRESENCE	mandatory	}
}

UnsuccessfulRL-InformationResponse-RL-SetupFailureTDD ::= SEQUENCE {
	rL-ID						RL-ID,
	cause						Cause,
	iE-Extensions				ProtocolExtensionContainer { {UnsuccessfulRL-InformationResponse-RL-SetupFailureTDD-ExtIEs} } OPTIONAL,
	...
}

UnsuccessfulRL-InformationResponse-RL-SetupFailureTDD-ExtIEs RNSAP-PROTOCOL-EXTENSION ::= {
	...
}

RadioLinkSetupFailureTDD-Extensions RNSAP-PROTOCOL-EXTENSION ::= {
	...
}

-- **************************************************************
--
-- RADIO LINK ADDITION REQUEST FDD
--
-- **************************************************************

RadioLinkAdditionRequestFDD ::= SEQUENCE {
	protocolIEs                     ProtocolIE-Container       {{RadioLinkAdditionRequestFDD-IEs}},
	protocolExtensions              ProtocolExtensionContainer {{RadioLinkAdditionRequestFDD-Extensions}}                   OPTIONAL,
	...
}

RadioLinkAdditionRequestFDD-IEs RNSAP-PROTOCOL-IES ::= {
	{ ID id-UL-SIRTarget				CRITICALITY reject	TYPE UL-SIR					PRESENCE mandatory	} |
	{ ID id-RL-InformationList-RL-AdditionRqstFDD	CRITICALITY notify	TYPE RL-InformationList-RL-AdditionRqstFDD	PRESENCE mandatory	}|
	{ ID id-Active-Pattern-Sequence-Information	CRITICALITY reject	TYPE Active-Pattern-Sequence-Information	 PRESENCE optional },
	...
}

RL-InformationList-RL-AdditionRqstFDD			::= SEQUENCE (SIZE (1..maxNrOfRLs-1)) OF ProtocolIE-Single-Container { {RL-Information-RL-AdditionRqstFDD-IEs} }

RL-Information-RL-AdditionRqstFDD-IEs RNSAP-PROTOCOL-IES ::= {
	{ ID id-RL-Information-RL-AdditionRqstFDD	CRITICALITY notify	TYPE RL-Information-RL-AdditionRqstFDD		PRESENCE mandatory	}
}

RL-Information-RL-AdditionRqstFDD ::= SEQUENCE {
	rL-ID							RL-ID,
	c-ID							C-ID,
	frameOffset						FrameOffset,
	chipOffset						ChipOffset,
	diversityControlField			DiversityControlField,
	primaryCPICH-EcNo				PrimaryCPICH-EcNo		OPTIONAL,
	not-Used-sSDT-CellID			NULL			OPTIONAL,
	transmitDiversityIndicator		TransmitDiversityIndicator		OPTIONAL,
	iE-Extensions					ProtocolExtensionContainer { {RL-Information-RL-AdditionRqstFDD-ExtIEs} } OPTIONAL,
	...
}

RL-Information-RL-AdditionRqstFDD-ExtIEs RNSAP-PROTOCOL-EXTENSION ::= {
	{ ID id-DLReferencePower	CRITICALITY ignore		EXTENSION	DL-Power		PRESENCE optional}|
	{ ID id-Enhanced-PrimaryCPICH-EcNo				CRITICALITY ignore	EXTENSION Enhanced-PrimaryCPICH-EcNo				PRESENCE optional	}|
	{ ID id-RL-Specific-DCH-Info					CRITICALITY ignore	EXTENSION RL-Specific-DCH-Info						PRESENCE optional	}|
	{ ID id-DelayedActivation 						CRITICALITY reject	EXTENSION DelayedActivation							PRESENCE optional }|
	{ ID id-RL-Specific-EDCH-Information			CRITICALITY reject	EXTENSION RL-Specific-EDCH-Information			PRESENCE optional }|
	{ ID id-EDCH-RL-Indication						CRITICALITY reject	EXTENSION EDCH-RL-Indication						PRESENCE optional }|
	{ ID id-SynchronisationIndicator				CRITICALITY ignore	EXTENSION SynchronisationIndicator				PRESENCE optional }|
	{ ID id-HSDSCH-PreconfigurationSetup			CRITICALITY ignore	EXTENSION HSDSCH-PreconfigurationSetup			PRESENCE optional }|
	{ ID id-Non-Serving-RL-Preconfig-Setup			CRITICALITY ignore	EXTENSION Non-Serving-RL-Preconfig-Setup			PRESENCE optional },
	...
}

RadioLinkAdditionRequestFDD-Extensions RNSAP-PROTOCOL-EXTENSION ::= {
	{ ID id-DPC-Mode									CRITICALITY reject	EXTENSION DPC-Mode													PRESENCE optional }|
	{ ID id-Permanent-NAS-UE-Identity					CRITICALITY ignore	EXTENSION Permanent-NAS-UE-Identity							PRESENCE optional }|
		{ ID id-Serving-EDCHRL-Id						CRITICALITY reject	EXTENSION EDCH-Serving-RL										PRESENCE optional }|
	{ ID id-Initial-DL-DPCH-TimingAdjustment-Allowed	CRITICALITY ignore	EXTENSION Initial-DL-DPCH-TimingAdjustment-Allowed		PRESENCE optional }|
	{ ID id-HS-DSCH-serving-cell-change-information		CRITICALITY reject	EXTENSION HS-DSCH-serving-cell-change-information		PRESENCE optional }|
	{ ID id-Serving-cell-change-CFN						CRITICALITY reject	EXTENSION CFN														PRESENCE optional }|
	{ ID id-EDPCH-Information							CRITICALITY reject	EXTENSION EDPCH-Information-RLAdditionReq-FDD				PRESENCE optional }|
	{ ID id-EDCH-FDD-Information						CRITICALITY reject	EXTENSION EDCH-FDD-Information									PRESENCE optional }|
	{ ID id-Additional-HS-Cell-Information-RL-Addition	CRITICALITY reject	EXTENSION Additional-HS-Cell-Information-RL-Addition-List	PRESENCE optional }|
	-- This IE shall be present if E-DPCH Information is present
	{ ID id-UE-AggregateMaximumBitRate					CRITICALITY ignore	EXTENSION UE-AggregateMaximumBitRate							PRESENCE optional	}|
	{ ID id-Additional-EDCH-Cell-Information-RL-Add-Req		CRITICALITY reject	EXTENSION Additional-EDCH-Cell-Information-RL-Add-Req			PRESENCE optional },
	...
}

Additional-HS-Cell-Information-RL-Addition-List	::= SEQUENCE (SIZE (1..maxNrOfHSDSCH-1)) OF Additional-HS-Cell-Information-RL-Addition-ItemIEs



Additional-HS-Cell-Information-RL-Addition-ItemIEs	::=SEQUENCE{
	hSPDSCH-RL-ID								RL-ID,
	c-ID										C-ID,
	hS-DSCH-FDD-Secondary-Serving-Information	HS-DSCH-FDD-Secondary-Serving-Information,
	iE-Extensions					ProtocolExtensionContainer { { Additional-HS-Cell-Information-RL-Addition-ItemIEs-ExtIEs} } OPTIONAL,
	...
}

Additional-HS-Cell-Information-RL-Addition-ItemIEs-ExtIEs	RNSAP-PROTOCOL-EXTENSION ::= {
	...
}

Additional-EDCH-Cell-Information-RL-Add-Req	::=SEQUENCE{
	setup-Or-Addition-Of-EDCH-On-secondary-UL-Frequency							Setup-Or-Addition-Of-EDCH-On-secondary-UL-Frequency,
	iE-Extensions					ProtocolExtensionContainer { { Additional-EDCH-Cell-Information-RL-Add-Req-ExtIEs} } OPTIONAL,
	...
}

Additional-EDCH-Cell-Information-RL-Add-Req-ExtIEs	RNSAP-PROTOCOL-EXTENSION ::= {
	...
}

Setup-Or-Addition-Of-EDCH-On-secondary-UL-Frequency::= CHOICE {
	setup			Additional-EDCH-Setup-Info,
	addition		Additional-EDCH-Cell-Information-To-Add-List,
	...
}

EDPCH-Information-RLAdditionReq-FDD::= SEQUENCE {
	maxSet-E-DPDCHs								Max-Set-E-DPDCHs,
	ul-PunctureLimit							PunctureLimit,
	e-TFCS-Information							E-TFCS-Information,
	e-TTI										E-TTI,
	e-DPCCH-PO									E-DPCCH-PO,
	e-RGCH-2-IndexStepThreshold					E-RGCH-2-IndexStepThreshold,
	e-RGCH-3-IndexStepThreshold					E-RGCH-3-IndexStepThreshold,
	hARQ-Info-for-E-DCH							HARQ-Info-for-E-DCH,
	iE-Extensions								ProtocolExtensionContainer { { EDPCH-Information-RLAdditionReq-FDD-ExtIEs} }		OPTIONAL,
	...
}

EDPCH-Information-RLAdditionReq-FDD-ExtIEs RNSAP-PROTOCOL-EXTENSION ::= {
{ ID id-HSDSCH-Configured-Indicator		CRITICALITY	reject	EXTENSION	HSDSCH-Configured-Indicator	PRESENCE mandatory}|
-- This shall be present for EDPCH configuration with HSDCH
{ ID id-MinimumReducedE-DPDCH-GainFactor		CRITICALITY ignore	EXTENSION MinimumReducedE-DPDCH-GainFactor	PRESENCE optional },
	...
}

-- **************************************************************
--
-- RADIO LINK ADDITION REQUEST TDD
--
-- **************************************************************

RadioLinkAdditionRequestTDD ::= SEQUENCE {
	protocolIEs                     ProtocolIE-Container       {{RadioLinkAdditionRequestTDD-IEs}},
	protocolExtensions              ProtocolExtensionContainer {{RadioLinkAdditionRequestTDD-Extensions}}                   OPTIONAL,
	...
}

RadioLinkAdditionRequestTDD-IEs RNSAP-PROTOCOL-IES ::= {
	{ ID id-RL-Information-RL-AdditionRqstTDD	CRITICALITY reject	TYPE RL-Information-RL-AdditionRqstTDD		PRESENCE mandatory	},
	...
}

RL-Information-RL-AdditionRqstTDD ::= SEQUENCE {
	rL-ID							RL-ID,
	c-ID							C-ID,
	frameOffset						FrameOffset,
	diversityControlField			DiversityControlField,
	primaryCCPCH-RSCP				PrimaryCCPCH-RSCP		OPTIONAL,
	dL-TimeSlot-ISCP-Info			DL-TimeSlot-ISCP-Info	OPTIONAL,
	--for 3.84Mcps TDD only
	iE-Extensions					ProtocolExtensionContainer { {RL-Information-RL-AdditionRqstTDD-ExtIEs} } OPTIONAL,
	...
}

RL-Information-RL-AdditionRqstTDD-ExtIEs RNSAP-PROTOCOL-EXTENSION ::= {
	{ ID id-DL-Timeslot-ISCP-LCR-Information-RL-AdditionRqstTDD	CRITICALITY reject	EXTENSION DL-TimeSlot-ISCP-LCR-Information		PRESENCE optional }|
	--for 1.28Mcps TDD only
	{ ID id-RL-Specific-DCH-Info	CRITICALITY ignore	EXTENSION RL-Specific-DCH-Info	PRESENCE optional }|
	{ ID id-DelayedActivation	CRITICALITY reject	EXTENSION DelayedActivation	PRESENCE optional }|
	{ ID id-UL-Synchronisation-Parameters-LCR	CRITICALITY reject	EXTENSION UL-Synchronisation-Parameters-LCR	PRESENCE optional }|
	-- Mandatory for 1.28Mcps TDD, Not Applicable to 3.84Mcps TDD or 7.68Mcps TDD
	{ ID id-PrimaryCCPCH-RSCP-Delta	CRITICALITY ignore	EXTENSION PrimaryCCPCH-RSCP-Delta	PRESENCE optional }|
	{ ID id-IdleIntervalConfigurationIndicator	CRITICALITY ignore	EXTENSION NULL	PRESENCE optional },
	...
}

RadioLinkAdditionRequestTDD-Extensions RNSAP-PROTOCOL-EXTENSION ::= {
	{ ID id-Permanent-NAS-UE-Identity				CRITICALITY ignore			EXTENSION Permanent-NAS-UE-Identity		PRESENCE optional	}|
	{ ID id-UL-CCTrCH-InformationList-RL-AdditionRqstTDD	CRITICALITY notify	EXTENSION UL-CCTrCH-InformationList-RL-AdditionRqstTDD	PRESENCE optional	} |
	{ ID id-DL-CCTrCH-InformationList-RL-AdditionRqstTDD	CRITICALITY notify	EXTENSION DL-CCTrCH-InformationList-RL-AdditionRqstTDD 	PRESENCE optional	}|
	{ ID id-HSDSCH-TDD-Information							CRITICALITY reject		EXTENSION HSDSCH-TDD-Information			PRESENCE optional	}|
	{ ID id-HSPDSCH-RL-ID									CRITICALITY reject		EXTENSION RL-ID									PRESENCE optional	}|
	{ ID id-E-DCH-Information								CRITICALITY reject		EXTENSION E-DCH-Information				PRESENCE optional	}|
	{ ID id-E-DCH-Serving-RL-ID								CRITICALITY reject		EXTENSION RL-ID				PRESENCE optional	}|
	{ ID id-E-DCH-768-Information							CRITICALITY reject		EXTENSION E-DCH-768-Information				PRESENCE optional	}|
	{ ID id-E-DCH-LCR-Information							CRITICALITY reject		EXTENSION E-DCH-LCR-Information				PRESENCE optional	}|
	{ ID id-ContinuousPacketConnectivity-DRX-InformationLCR		CRITICALITY reject		EXTENSION ContinuousPacketConnectivity-DRX-InformationLCR			PRESENCE optional }|
	{ ID id-HS-DSCH-Semi-PersistentScheduling-Information-LCR	CRITICALITY reject		EXTENSION HS-DSCH-Semi-PersistentScheduling-Information-LCR		PRESENCE optional }|
	{ ID id-E-DCH-Semi-PersistentScheduling-Information-LCR		CRITICALITY reject		EXTENSION E-DCH-Semi-PersistentScheduling-Information-LCR		PRESENCE optional }|
	{ ID id-DCH-MeasurementType-Indicator					CRITICALITY reject		EXTENSION DCH-MeasurementType-Indicator	PRESENCE optional},
	...
}

UL-CCTrCH-InformationList-RL-AdditionRqstTDD	::= SEQUENCE (SIZE (1..maxNrOfCCTrCHs)) OF ProtocolIE-Single-Container { {UL-CCTrCH-InformationItemIEs-RL-AdditionRqstTDD} }

UL-CCTrCH-InformationItemIEs-RL-AdditionRqstTDD RNSAP-PROTOCOL-IES ::= {
	{ ID id-UL-CCTrCH-InformationItem-RL-AdditionRqstTDD	CRITICALITY notify	TYPE UL-CCTrCH-InformationItem-RL-AdditionRqstTDD 	PRESENCE optional},
	...
}

UL-CCTrCH-InformationItem-RL-AdditionRqstTDD ::= SEQUENCE {
	cCTrCH-ID					CCTrCH-ID,
	uplinkStepSizeLCR			TDD-TPC-UplinkStepSize-LCR    OPTIONAL,
	-- Applicable to 1.28Mcps TDD only
	iE-Extensions				ProtocolExtensionContainer { {UL-CCTrCH-InformationItem-RL-AdditionRqstTDD-ExtIEs} } OPTIONAL,
	...
}

UL-CCTrCH-InformationItem-RL-AdditionRqstTDD-ExtIEs RNSAP-PROTOCOL-EXTENSION ::= {
	...
}

DL-CCTrCH-InformationList-RL-AdditionRqstTDD	::= SEQUENCE (SIZE (1..maxNrOfCCTrCHs)) OF ProtocolIE-Single-Container { {DL-CCTrCH-InformationItemIEs-RL-AdditionRqstTDD} }

DL-CCTrCH-InformationItemIEs-RL-AdditionRqstTDD RNSAP-PROTOCOL-IES ::= {
	{ ID id-DL-CCTrCH-InformationItem-RL-AdditionRqstTDD	CRITICALITY notify	TYPE DL-CCTrCH-InformationItem-RL-AdditionRqstTDD	PRESENCE optional},
	...
}

DL-CCTrCH-InformationItem-RL-AdditionRqstTDD ::= SEQUENCE {
	cCTrCH-ID					CCTrCH-ID,
	downlinkStepSize			TDD-TPC-DownlinkStepSize   OPTIONAL,
	iE-Extensions				ProtocolExtensionContainer { {DL-CCTrCH-InformationItem-RL-AdditionRqstTDD-ExtIEs} } OPTIONAL,
	...
}

DL-CCTrCH-InformationItem-RL-AdditionRqstTDD-ExtIEs RNSAP-PROTOCOL-EXTENSION ::= {
	...
}

-- **************************************************************
--
-- RADIO LINK ADDITION RESPONSE FDD
--
-- **************************************************************

RadioLinkAdditionResponseFDD ::= SEQUENCE {
	protocolIEs                     ProtocolIE-Container       {{RadioLinkAdditionResponseFDD-IEs}},
	protocolExtensions              ProtocolExtensionContainer {{RadioLinkAdditionResponseFDD-Extensions}}                   OPTIONAL,
	...
}

RadioLinkAdditionResponseFDD-IEs RNSAP-PROTOCOL-IES ::= {
	{ ID id-RL-InformationResponseList-RL-AdditionRspFDD	CRITICALITY ignore	TYPE RL-InformationResponseList-RL-AdditionRspFDD 		PRESENCE mandatory	} |
	{ ID id-CriticalityDiagnostics			CRITICALITY ignore	TYPE CriticalityDiagnostics			PRESENCE optional	},
	...
}

RL-InformationResponseList-RL-AdditionRspFDD 		::= SEQUENCE (SIZE (1..maxNrOfRLs-1)) OF ProtocolIE-Single-Container { {RL-InformationResponseItemIEs-RL-AdditionRspFDD} }

RL-InformationResponseItemIEs-RL-AdditionRspFDD RNSAP-PROTOCOL-IES ::= {
	{ ID id-RL-InformationResponseItem-RL-AdditionRspFDD		CRITICALITY ignore	TYPE RL-InformationResponseItem-RL-AdditionRspFDD 	PRESENCE mandatory	}
}

RL-InformationResponseItem-RL-AdditionRspFDD ::= SEQUENCE {
	rL-ID							RL-ID,
	rL-Set-ID						RL-Set-ID,
	uRA-Information					URA-Information		OPTIONAL,
	sAI								SAI,
	gA-Cell							GA-Cell		OPTIONAL,
	gA-AccessPointPosition			GA-AccessPointPosition	OPTIONAL,
	received-total-wide-band-power	Received-total-wide-band-power,
	not-Used-secondary-CCPCH-Info			NULL		OPTIONAL,
	dl-CodeInformation				DL-CodeInformationList-RL-AdditionRspFDD,
	diversityIndication				DiversityIndication-RL-AdditionRspFDD,

	sSDT-SupportIndicator				SSDT-SupportIndicator,
	minUL-SIR							UL-SIR,
	maxUL-SIR							UL-SIR,
	closedlooptimingadjustmentmode		Closedlooptimingadjustmentmode	OPTIONAL,
	maximumAllowedULTxPower				MaximumAllowedULTxPower,
	maximumDLTxPower					DL-Power,
	minimumDLTxPower					DL-Power,
	neighbouring-UMTS-CellInformation	Neighbouring-UMTS-CellInformation	OPTIONAL,
	neighbouring-GSM-CellInformation	Neighbouring-GSM-CellInformation OPTIONAL,
	pC-Preamble							PC-Preamble,
	sRB-Delay							SRB-Delay,
	primaryCPICH-Power					PrimaryCPICH-Power,
	iE-Extensions						ProtocolExtensionContainer { {RL-InformationResponseItem-RL-AdditionRspFDD-ExtIEs} } OPTIONAL,
	...
}

RL-InformationResponseItem-RL-AdditionRspFDD-ExtIEs RNSAP-PROTOCOL-EXTENSION ::= {
	{ ID id-GA-CellAdditionalShapes					CRITICALITY ignore	EXTENSION GA-CellAdditionalShapes							PRESENCE optional }|
	{ ID id-DL-PowerBalancing-ActivationIndicator	CRITICALITY ignore	EXTENSION DL-PowerBalancing-ActivationIndicator		PRESENCE optional }|
	{ ID id-HCS-Prio								CRITICALITY ignore	EXTENSION HCS-Prio												PRESENCE optional }|
	{ ID id-Active-MBMS-Bearer-ServiceFDD-PFL		CRITICALITY ignore	EXTENSION Active-MBMS-Bearer-Service-ListFDD-PFL		PRESENCE optional }|
	{ ID id-EDCH-RLSet-Id							CRITICALITY ignore	EXTENSION RL-Set-ID												PRESENCE optional }|
	{ ID id-EDCH-FDD-DL-ControlChannelInformation	CRITICALITY ignore	EXTENSION EDCH-FDD-DL-ControlChannelInformation		PRESENCE optional }|
	{ ID id-Initial-DL-DPCH-TimingAdjustment		CRITICALITY ignore	EXTENSION DL-DPCH-TimingAdjustment							PRESENCE optional }|
	{ ID id-F-DPCH-SlotFormat						CRITICALITY ignore	EXTENSION F-DPCH-SlotFormat									PRESENCE optional }|
	{ ID id-Neighbouring-E-UTRA-CellInformation		CRITICALITY ignore	EXTENSION Neighbouring-E-UTRA-CellInformation			PRESENCE optional }|
	{ ID id-HSDSCH-PreconfigurationInfo				CRITICALITY ignore	EXTENSION HSDSCH-PreconfigurationInfo						PRESENCE optional }|
	{ ID id-Non-Serving-RL-Preconfig-Info			CRITICALITY ignore	EXTENSION Non-Serving-RL-Preconfig-Info					PRESENCE optional },
	...
}

DL-CodeInformationList-RL-AdditionRspFDD ::= ProtocolIE-Single-Container {{ DL-CodeInformationListIEs-RL-AdditionRspFDD }}

DL-CodeInformationListIEs-RL-AdditionRspFDD RNSAP-PROTOCOL-IES ::= {
	{ ID id-FDD-DL-CodeInformation   CRITICALITY ignore	TYPE FDD-DL-CodeInformation		PRESENCE mandatory }
}

DiversityIndication-RL-AdditionRspFDD ::= CHOICE {
	combining						Combining-RL-AdditionRspFDD,
	nonCombining					NonCombining-RL-AdditionRspFDD
}

Combining-RL-AdditionRspFDD ::= SEQUENCE {
	rL-ID						RL-ID,
	iE-Extensions				ProtocolExtensionContainer { { CombiningItem-RL-AdditionRspFDD-ExtIEs} } OPTIONAL,
	...
}

CombiningItem-RL-AdditionRspFDD-ExtIEs RNSAP-PROTOCOL-EXTENSION ::= {
	{ ID id-DCH-InformationResponse			CRITICALITY ignore	EXTENSION DCH-InformationResponse			PRESENCE optional	}|
	{ ID id-EDCH-FDD-InformationResponse	CRITICALITY ignore	EXTENSION EDCH-FDD-InformationResponse			PRESENCE optional	},
	...
}

NonCombining-RL-AdditionRspFDD ::= SEQUENCE {
	dCH-InformationResponse					DCH-InformationResponse,
	iE-Extensions								ProtocolExtensionContainer { { NonCombiningItem-RL-AdditionRspFDD-ExtIEs} } OPTIONAL,
	...
}

NonCombiningItem-RL-AdditionRspFDD-ExtIEs RNSAP-PROTOCOL-EXTENSION ::= {
	{ ID id-EDCH-FDD-InformationResponse	CRITICALITY ignore	EXTENSION EDCH-FDD-InformationResponse			PRESENCE optional	},
	...
}

RadioLinkAdditionResponseFDD-Extensions RNSAP-PROTOCOL-EXTENSION ::= {
	{ ID id-HS-DSCH-serving-cell-change-informationResponse	CRITICALITY ignore	EXTENSION HS-DSCH-serving-cell-change-informationResponse			PRESENCE optional}|
	{ ID id-E-DCH-Serving-cell-change-informationResponse	CRITICALITY ignore	EXTENSION E-DCH-Serving-cell-change-informationResponse				PRESENCE optional}|
	{ ID id-MAChs-ResetIndicator							CRITICALITY ignore	EXTENSION MAChs-ResetIndicator												PRESENCE optional}|
	{ ID id-Additional-HS-Cell-Change-Information-Response	CRITICALITY ignore	EXTENSION Additional-HS-Cell-Change-Information-Response-List		PRESENCE optional}|
	{ ID id-Additional-EDCH-Cell-Information-Response-RLAdd	CRITICALITY ignore	EXTENSION Additional-EDCH-Cell-Information-Response-RLAddList	PRESENCE optional },
	...
}

Additional-HS-Cell-Change-Information-Response-List	::= SEQUENCE (SIZE (1..maxNrOfHSDSCH-1)) OF Additional-HS-Cell-Change-Information-Response-ItemIEs



Additional-HS-Cell-Change-Information-Response-ItemIEs	::=SEQUENCE{
	hSPDSCH-RL-ID												RL-ID,
	hSDSCH-RNTI													HSDSCH-RNTI,
	hS-DSCH-Secondary-Serving-Cell-Change-Information-Response	HS-DSCH-Secondary-Serving-Cell-Change-Information-Response,
	iE-Extensions					ProtocolExtensionContainer { { Additional-HS-Cell-Change-Information-Response-ItemIEs-ExtIEs} } OPTIONAL,
	...
}

Additional-HS-Cell-Change-Information-Response-ItemIEs-ExtIEs	RNSAP-PROTOCOL-EXTENSION ::= {
	...
}


-- **************************************************************
--
-- RADIO LINK ADDITION RESPONSE TDD
--
-- **************************************************************

RadioLinkAdditionResponseTDD ::= SEQUENCE {
	protocolIEs                     ProtocolIE-Container       {{RadioLinkAdditionResponseTDD-IEs}},
	protocolExtensions              ProtocolExtensionContainer {{RadioLinkAdditionResponseTDD-Extensions}}                   OPTIONAL,
	...
}

RadioLinkAdditionResponseTDD-IEs RNSAP-PROTOCOL-IES ::= {
	{ ID id-RL-InformationResponse-RL-AdditionRspTDD		CRITICALITY ignore	TYPE RL-InformationResponse-RL-AdditionRspTDD 	PRESENCE optional	} |
	--Mandatory for 3.84Mcps TDD only
	{ ID id-CriticalityDiagnostics			CRITICALITY ignore	TYPE CriticalityDiagnostics			PRESENCE optional	},
	...
}

RL-InformationResponse-RL-AdditionRspTDD ::= SEQUENCE {
	rL-ID								RL-ID,
	uRA-Information						URA-Information		OPTIONAL,
	sAI									SAI,
	gA-Cell								GA-Cell		OPTIONAL,
	gA-AccessPointPosition				GA-AccessPointPosition	OPTIONAL,
	ul-TimeSlot-ISCP-Info				UL-TimeSlot-ISCP-Info,
	minUL-SIR							UL-SIR,
	maxUL-SIR							UL-SIR,
	maximumAllowedULTxPower				MaximumAllowedULTxPower,
	maximumDLTxPower					DL-Power,
	minimumDLTxPower					DL-Power,
	pCCPCH-Power						PCCPCH-Power,
	timingAdvanceApplied				TimingAdvanceApplied,
	alphaValue							AlphaValue,
	ul-PhysCH-SF-Variation				UL-PhysCH-SF-Variation,
	synchronisationConfiguration		SynchronisationConfiguration,
	secondary-CCPCH-Info-TDD			Secondary-CCPCH-Info-TDD						OPTIONAL,
	ul-CCTrCHInformation				UL-CCTrCHInformationList-RL-AdditionRspTDD		OPTIONAL,
	dl-CCTrCHInformation				DL-CCTrCHInformationList-RL-AdditionRspTDD		OPTIONAL,
	dCH-Information						DCH-Information-RL-AdditionRspTDD				OPTIONAL,
	dSCH-InformationResponse			DSCH-InformationResponse-RL-AdditionRspTDD		OPTIONAL,
	uSCH-InformationResponse			USCH-InformationResponse-RL-AdditionRspTDD		OPTIONAL,
	neighbouring-UMTS-CellInformation	Neighbouring-UMTS-CellInformation 	OPTIONAL,
	neighbouring-GSM-CellInformation	Neighbouring-GSM-CellInformation OPTIONAL,
	iE-Extensions						ProtocolExtensionContainer { {RL-InformationResponse-RL-AdditionRspTDD-ExtIEs} } OPTIONAL,
	...
}

RL-InformationResponse-RL-AdditionRspTDD-ExtIEs RNSAP-PROTOCOL-EXTENSION ::= {
	{ ID id-GA-CellAdditionalShapes					CRITICALITY	ignore	EXTENSION	GA-CellAdditionalShapes						PRESENCE optional }|
	{ ID id-HCS-Prio								CRITICALITY	ignore	EXTENSION	HCS-Prio											PRESENCE optional }|
	{ ID id-Neighbouring-E-UTRA-CellInformation		CRITICALITY ignore	EXTENSION Neighbouring-E-UTRA-CellInformation			PRESENCE optional },
	...
}

UL-CCTrCHInformationList-RL-AdditionRspTDD ::= ProtocolIE-Single-Container {{UL-CCTrCHInformationListIEs-RL-AdditionRspTDD}}

UL-CCTrCHInformationListIEs-RL-AdditionRspTDD RNSAP-PROTOCOL-IES ::= {
	{ ID id-UL-CCTrCH-InformationListIE-RL-AdditionRspTDD   CRITICALITY ignore	TYPE UL-CCTrCHInformationListIE-RL-AdditionRspTDD		PRESENCE mandatory }
}

UL-CCTrCHInformationListIE-RL-AdditionRspTDD ::= SEQUENCE (SIZE (1..maxNrOfCCTrCHs)) OF UL-CCTrCHInformationItem-RL-AdditionRspTDD

UL-CCTrCHInformationItem-RL-AdditionRspTDD ::= SEQUENCE {
	cCTrCH-ID					CCTrCH-ID,
	ul-DPCH-Information				UL-DPCH-InformationList-RL-AdditionRspTDD		OPTIONAL,
	iE-Extensions					ProtocolExtensionContainer { {UL-CCTrCHInformationItem-RL-AdditionRspTDD-ExtIEs} } OPTIONAL,
	...
}

UL-CCTrCHInformationItem-RL-AdditionRspTDD-ExtIEs RNSAP-PROTOCOL-EXTENSION ::= {
	...
}

UL-DPCH-InformationList-RL-AdditionRspTDD ::= ProtocolIE-Single-Container { {UL-DPCH-InformationListIEs-RL-AdditionRspTDD} }

UL-DPCH-InformationListIEs-RL-AdditionRspTDD RNSAP-PROTOCOL-IES ::= {
	{ ID id-UL-DPCH-InformationItem-RL-AdditionRspTDD		CRITICALITY ignore	TYPE UL-DPCH-InformationItem-RL-AdditionRspTDD  PRESENCE mandatory	}
}

UL-DPCH-InformationItem-RL-AdditionRspTDD ::= SEQUENCE {
	repetitionPeriod				RepetitionPeriod,
	repetitionLength				RepetitionLength,
	tDD-DPCHOffset					TDD-DPCHOffset,
	uL-Timeslot-Information			UL-Timeslot-Information,
	iE-Extensions					ProtocolExtensionContainer { {UL-DPCH-InformationItem-RL-AdditionRspTDD-ExtIEs} } OPTIONAL,
	...
}

UL-DPCH-InformationItem-RL-AdditionRspTDD-ExtIEs RNSAP-PROTOCOL-EXTENSION ::= {
	...
}

DL-CCTrCHInformationList-RL-AdditionRspTDD ::= ProtocolIE-Single-Container {{DL-CCTrCHInformationListIEs-RL-AdditionRspTDD}}

DL-CCTrCHInformationListIEs-RL-AdditionRspTDD RNSAP-PROTOCOL-IES ::= {
	{ ID id-DL-CCTrCH-InformationListIE-RL-AdditionRspTDD   CRITICALITY ignore	TYPE DL-CCTrCHInformationListIE-RL-AdditionRspTDD		PRESENCE mandatory }
}

DL-CCTrCHInformationListIE-RL-AdditionRspTDD ::= SEQUENCE (SIZE (1..maxNrOfCCTrCHs)) OF DL-CCTrCHInformationItem-RL-AdditionRspTDD

DL-CCTrCHInformationItem-RL-AdditionRspTDD ::= SEQUENCE {
	cCTrCH-ID					CCTrCH-ID,
	dl-DPCH-Information				DL-DPCH-InformationList-RL-AdditionRspTDD		OPTIONAL,
	iE-Extensions					ProtocolExtensionContainer { {DL-CCTrCHInformationItem-RL-AdditionRspTDD-ExtIEs} } OPTIONAL,
	...
}

DL-CCTrCHInformationItem-RL-AdditionRspTDD-ExtIEs RNSAP-PROTOCOL-EXTENSION ::= {
	{ ID id-CCTrCH-Maximum-DL-Power-RL-AdditionRspTDD		CRITICALITY ignore		EXTENSION  DL-Power    PRESENCE optional	}| -- this is a DCH type CCTrCH power
	{ ID id-CCTrCH-Minimum-DL-Power-RL-AdditionRspTDD		CRITICALITY ignore		EXTENSION  DL-Power    PRESENCE optional	}, -- this is a DCH type CCTrCH power
	...
}

DL-DPCH-InformationList-RL-AdditionRspTDD ::= ProtocolIE-Single-Container { {DL-DPCH-InformationListIEs-RL-AdditionRspTDD} }

DL-DPCH-InformationListIEs-RL-AdditionRspTDD RNSAP-PROTOCOL-IES ::= {
	{ ID id-DL-DPCH-InformationItem-RL-AdditionRspTDD		CRITICALITY ignore	TYPE DL-DPCH-InformationItem-RL-AdditionRspTDD  PRESENCE mandatory	}
}

DL-DPCH-InformationItem-RL-AdditionRspTDD ::= SEQUENCE {
	repetitionPeriod				RepetitionPeriod,
	repetitionLength				RepetitionLength,
	tDD-DPCHOffset					TDD-DPCHOffset,
	dL-Timeslot-Information			DL-Timeslot-Information,
	iE-Extensions					ProtocolExtensionContainer { {DL-DPCH-InformationItem-RL-AdditionRspTDD-ExtIEs} } OPTIONAL,
	...
}

DL-DPCH-InformationItem-RL-AdditionRspTDD-ExtIEs RNSAP-PROTOCOL-EXTENSION ::= {
	...
}

DCH-Information-RL-AdditionRspTDD ::= SEQUENCE {
	diversityIndication					DiversityIndication-RL-AdditionRspTDD,

	iE-Extensions					ProtocolExtensionContainer { { DCH-Information-RL-AdditionRspTDD-ExtIEs} } OPTIONAL,
	...
}

DCH-Information-RL-AdditionRspTDD-ExtIEs RNSAP-PROTOCOL-EXTENSION ::= {
	...
}

DiversityIndication-RL-AdditionRspTDD ::= CHOICE {
	combining		Combining-RL-AdditionRspTDD,
	nonCombining	NonCombining-RL-AdditionRspTDD
}

Combining-RL-AdditionRspTDD	::= SEQUENCE {
	rL-ID						RL-ID,
	iE-Extensions				ProtocolExtensionContainer { { CombiningItem-RL-AdditionRspTDD-ExtIEs} } OPTIONAL,
	...
}

CombiningItem-RL-AdditionRspTDD-ExtIEs RNSAP-PROTOCOL-EXTENSION ::= {
	{ ID id-DCH-InformationResponse			CRITICALITY ignore	EXTENSION DCH-InformationResponse			PRESENCE optional	},
	...
}

NonCombining-RL-AdditionRspTDD	::= SEQUENCE {
	dCH-InformationResponse		DCH-InformationResponse,
	iE-Extensions					ProtocolExtensionContainer { { NonCombiningItem-RL-AdditionRspTDD-ExtIEs} } OPTIONAL,
	...
}

NonCombiningItem-RL-AdditionRspTDD-ExtIEs RNSAP-PROTOCOL-EXTENSION ::= {
	...
}

DSCH-InformationResponse-RL-AdditionRspTDD ::= ProtocolIE-Single-Container {{DSCH-InformationListIEs-RL-AdditionRspTDD}}

DSCH-InformationListIEs-RL-AdditionRspTDD RNSAP-PROTOCOL-IES ::= {
	{ ID id-DSCH-InformationListIE-RL-AdditionRspTDD	CRITICALITY ignore	TYPE DSCH-InformationListIE-RL-AdditionRspTDD		PRESENCE mandatory }
}

DSCH-InformationListIE-RL-AdditionRspTDD ::= SEQUENCE (SIZE(0..maxNoOfDSCHs)) OF DSCHInformationItem-RL-AdditionRspTDD

DSCHInformationItem-RL-AdditionRspTDD ::= SEQUENCE {
	dsch-ID					DSCH-ID,
	transportFormatManagement	TransportFormatManagement,
	dSCH-FlowControlInformation		DSCH-FlowControlInformation,
	diversityIndication		DiversityIndication-RL-AdditionRspTDD2 OPTIONAL,
	-- diversityIndication present, if CHOICE = nonCombining
	iE-Extensions			ProtocolExtensionContainer { {DSCHInformationItem-RL-AdditionRspTDD-ExtIEs} } OPTIONAL,
	...
}

DSCHInformationItem-RL-AdditionRspTDD-ExtIEs RNSAP-PROTOCOL-EXTENSION ::= {
	...
}

DiversityIndication-RL-AdditionRspTDD2 ::= SEQUENCE {
	bindingID				BindingID	OPTIONAL,
	transportLayerAddress	TransportLayerAddress	OPTIONAL,
	iE-Extensions			ProtocolExtensionContainer { {DiversityIndication-RL-AdditionRspTDD2-ExtIEs} } OPTIONAL,
	...
}
DiversityIndication-RL-AdditionRspTDD2-ExtIEs RNSAP-PROTOCOL-EXTENSION ::= {
	...
}

USCH-InformationResponse-RL-AdditionRspTDD ::= ProtocolIE-Single-Container {{USCH-InformationListIEs-RL-AdditionRspTDD}}

USCH-InformationListIEs-RL-AdditionRspTDD RNSAP-PROTOCOL-IES ::= {
	{ ID id-USCH-InformationListIE-RL-AdditionRspTDD	CRITICALITY ignore	TYPE USCH-InformationListIE-RL-AdditionRspTDD		PRESENCE mandatory }
}

USCH-InformationListIE-RL-AdditionRspTDD ::= SEQUENCE (SIZE(0..maxNoOfUSCHs)) OF USCHInformationItem-RL-AdditionRspTDD

USCHInformationItem-RL-AdditionRspTDD ::= SEQUENCE {
	uSCH-ID					USCH-ID,
	transportFormatManagement	TransportFormatManagement,
	diversityIndication		DiversityIndication-RL-AdditionRspTDD2 OPTIONAL,
	-- diversityIndication present, if CHOICE = nonCombining
	iE-Extensions			ProtocolExtensionContainer { {USCHInformationItem-RL-AdditionRspTDD-ExtIEs} } OPTIONAL,
	...
}

USCHInformationItem-RL-AdditionRspTDD-ExtIEs RNSAP-PROTOCOL-EXTENSION ::= {
	...
}

RadioLinkAdditionResponseTDD-Extensions RNSAP-PROTOCOL-EXTENSION ::= {
	{ ID id-RL-LCR-InformationResponse-RL-AdditionRspTDD	CRITICALITY ignore		EXTENSION 	RL-LCR-InformationResponse-RL-AdditionRspTDD		PRESENCE optional	}|
	--Mandatory for 1.28Mcps TDD only
	{ ID id-Active-MBMS-Bearer-ServiceTDD-PFL				CRITICALITY ignore		EXTENSION Active-MBMS-Bearer-Service-ListTDD-PFL						PRESENCE optional}|
	{ ID id-HSDSCH-TDD-Information-Response					CRITICALITY ignore		EXTENSION HSDSCH-TDD-Information-Response							PRESENCE optional }|
	{ ID id-DSCH-RNTI										CRITICALITY ignore		EXTENSION DSCH-RNTI															PRESENCE optional }|
	{ ID id-RL-InformationResponse-RL-AdditionRspTDD768		CRITICALITY ignore		EXTENSION RL-InformationResponse-RL-AdditionRspTDD768					PRESENCE optional}|
	{ ID id-E-DCH-Information-Response						CRITICALITY ignore		EXTENSION E-DCH-Information-Response									PRESENCE optional	}|
	{ ID id-E-DCH-768-Information-Response					CRITICALITY ignore		EXTENSION E-DCH-768-Information-Response								PRESENCE optional	}|
	{ ID id-E-DCH-LCR-Information-Response					CRITICALITY ignore		EXTENSION E-DCH-LCR-Information-Response								PRESENCE optional	}|
	{ ID id-ContinuousPacketConnectivity-DRX-Information-ResponseLCR				CRITICALITY ignore		EXTENSION ContinuousPacketConnectivity-DRX-Information-ResponseLCR			PRESENCE optional	}|
	{ ID id-HS-DSCH-Semi-PersistentScheduling-Information-ResponseLCR		CRITICALITY ignore		EXTENSION HS-DSCH-Semi-PersistentScheduling-Information-ResponseLCR			PRESENCE optional	}|
	{ ID id-E-DCH-Semi-PersistentScheduling-Information-ResponseLCR		CRITICALITY ignore			EXTENSION E-DCH-Semi-PersistentScheduling-Information-ResponseLCR			PRESENCE optional}|
	{ ID id-DCH-MeasurementOccasion-Information				CRITICALITY reject		EXTENSION DCH-MeasurementOccasion-Information							PRESENCE optional},
	...
}

RL-LCR-InformationResponse-RL-AdditionRspTDD ::= SEQUENCE {
	rL-ID						RL-ID,
	uRA-Information				URA-Information,
	sAI							SAI,
	gA-Cell						GA-Cell		OPTIONAL,
	gA-AccessPointPosition		GA-AccessPointPosition	OPTIONAL,
	ul-TimeSlot-ISCP-LCR-Info	UL-TimeSlot-ISCP-LCR-Info,
	maxUL-SIR					UL-SIR,
	minUL-SIR					UL-SIR,
	pCCPCH-Power				PCCPCH-Power,
	maximumAllowedULTxPower		MaximumAllowedULTxPower,
	maximumDLTxPower			DL-Power,
	minimumDLTxPower			DL-Power,
	alphaValue					AlphaValue,
	ul-PhysCH-SF-Variation		UL-PhysCH-SF-Variation,
	synchronisationConfiguration		SynchronisationConfiguration,
	secondary-LCR-CCPCH-Info-TDD		Secondary-LCR-CCPCH-Info-TDD						OPTIONAL,
	ul-CCTrCH-LCR-Information			UL-CCTrCH-LCR-InformationList-RL-AdditionRspTDD		OPTIONAL,
	dl-CCTrCH-LCR-Information			DL-CCTrCH-LCR-InformationList-RL-AdditionRspTDD		OPTIONAL,
	dCH-InformationResponse				DCH-InformationResponseList-RL-AdditionRspTDD	OPTIONAL,
	dsch-LCR-InformationResponse		DSCH-LCR-InformationResponse-RL-AdditionRspTDD	OPTIONAL,
	usch-LCR-InformationResponse			USCH-LCR-InformationResponse-RL-AdditionRspTDD	OPTIONAL,
	neighbouring-UMTS-CellInformation			Neighbouring-UMTS-CellInformation	OPTIONAL,
	neighbouring-GSM-CellInformation			Neighbouring-GSM-CellInformation			 OPTIONAL,
	iE-Extensions								ProtocolExtensionContainer { { RL-LCR-InformationResponseList-RL-AdditionRspTDD-ExtIEs} }		OPTIONAL,
	...
}

RL-LCR-InformationResponseList-RL-AdditionRspTDD-ExtIEs RNSAP-PROTOCOL-EXTENSION ::= {
	{ ID id-GA-CellAdditionalShapes					CRITICALITY	ignore	EXTENSION	GA-CellAdditionalShapes						PRESENCE optional }|
	{ ID id-HCS-Prio								CRITICALITY	ignore	EXTENSION	HCS-Prio											PRESENCE optional }|
	{ ID id-UL-TimingAdvanceCtrl-LCR				CRITICALITY ignore	EXTENSION	UL-TimingAdvanceCtrl-LCR						PRESENCE optional }|
	--Mandatory for 1.28Mcps TDD only
	{ ID id-PowerControlGAP							CRITICALITY ignore	EXTENSION ControlGAP										PRESENCE optional }|
	-- Applicable to 1.28Mcps TDD only
	{ ID id-UARFCNforNt								CRITICALITY ignore	EXTENSION UARFCN											PRESENCE optional }|
	-- Applicable to 1.28Mcps TDD only
	{ ID id-Neighbouring-E-UTRA-CellInformation		CRITICALITY ignore	EXTENSION Neighbouring-E-UTRA-CellInformation			PRESENCE optional }|
	{ ID id-IdleIntervalInformation							CRITICALITY ignore	EXTENSION	IdleIntervalInformation				PRESENCE optional },
	...
}

UL-CCTrCH-LCR-InformationList-RL-AdditionRspTDD ::= ProtocolIE-Single-Container {{UL-CCTrCH-LCR-InformationListIEs-RL-AdditionRspTDD }}

UL-CCTrCH-LCR-InformationListIEs-RL-AdditionRspTDD RNSAP-PROTOCOL-IES ::= {
	{ ID id-UL-CCTrCH-LCR-InformationListIE-RL-AdditionRspTDD   CRITICALITY ignore	TYPE UL-CCTrCH-LCR-InformationListIE-RL-AdditionRspTDD		PRESENCE mandatory }
}

UL-CCTrCH-LCR-InformationListIE-RL-AdditionRspTDD ::= SEQUENCE (SIZE (1..maxNrOfCCTrCHsLCR)) OF UL-CCTrCH-LCR-InformationItem-RL-AdditionRspTDD

UL-CCTrCH-LCR-InformationItem-RL-AdditionRspTDD ::= SEQUENCE {
	cCTrCH-ID					CCTrCH-ID,
	ul-DPCH-LCR-Information				UL-DPCH-LCR-InformationList-RL-AdditionRspTDD		OPTIONAL,
	iE-Extensions					ProtocolExtensionContainer { {UL-CCTrCH-LCR-InformationItem-RL-AdditionRspTDD-ExtIEs} } OPTIONAL,
	...
}

UL-CCTrCH-LCR-InformationItem-RL-AdditionRspTDD-ExtIEs RNSAP-PROTOCOL-EXTENSION ::= {
	...
}

UL-DPCH-LCR-InformationList-RL-AdditionRspTDD ::= ProtocolIE-Single-Container { {UL-DPCH-LCR-InformationListIEs-RL-AdditionRspTDD} }

UL-DPCH-LCR-InformationListIEs-RL-AdditionRspTDD RNSAP-PROTOCOL-IES ::= {
	{ ID id-UL-DPCH-LCR-InformationItem-RL-AdditionRspTDD		CRITICALITY ignore	TYPE UL-DPCH-LCR-InformationItem-RL-AdditionRspTDD  PRESENCE mandatory	}
}

UL-DPCH-LCR-InformationItem-RL-AdditionRspTDD ::= SEQUENCE {
	repetitionPeriod				RepetitionPeriod,
	repetitionLength				RepetitionLength,
	tDD-DPCHOffset					TDD-DPCHOffset,
	uL-TimeslotLCR-Information		UL-TimeslotLCR-Information,
	iE-Extensions					ProtocolExtensionContainer { {UL-DPCH-LCR-InformationItem-RL-AdditionRspTDD-ExtIEs} } OPTIONAL,
	...
}

UL-DPCH-LCR-InformationItem-RL-AdditionRspTDD-ExtIEs RNSAP-PROTOCOL-EXTENSION ::= {
	...
}

DL-CCTrCH-LCR-InformationList-RL-AdditionRspTDD ::= ProtocolIE-Single-Container {{DL-CCTrCH-LCR-InformationListIEs-RL-AdditionRspTDD}}

DL-CCTrCH-LCR-InformationListIEs-RL-AdditionRspTDD RNSAP-PROTOCOL-IES ::= {
	{ ID id-DL-CCTrCH-LCR-InformationListIE-RL-AdditionRspTDD   CRITICALITY ignore	TYPE DL-CCTrCH-LCR-InformationListIE-RL-AdditionRspTDD  PRESENCE mandatory }
}

DL-CCTrCH-LCR-InformationListIE-RL-AdditionRspTDD ::= SEQUENCE (SIZE (1..maxNrOfCCTrCHsLCR)) OF DL-CCTrCH-LCR-InformationItem-RL-AdditionRspTDD

DL-CCTrCH-LCR-InformationItem-RL-AdditionRspTDD ::= SEQUENCE {
	cCTrCH-ID					CCTrCH-ID,
	dl-DPCH-LCR-Information		DL-DPCH-LCR-InformationList-RL-AdditionRspTDD		OPTIONAL,
	iE-Extensions				ProtocolExtensionContainer { {DL-CCTrCH-LCR-InformationItem-RL-AdditionRspTDD-ExtIEs} } OPTIONAL,
	...
}

DL-CCTrCH-LCR-InformationItem-RL-AdditionRspTDD-ExtIEs RNSAP-PROTOCOL-EXTENSION ::= {
	...
}

DL-DPCH-LCR-InformationList-RL-AdditionRspTDD ::= ProtocolIE-Single-Container { {DL-DPCH-LCR-InformationListIEs-RL-AdditionRspTDD} }

DL-DPCH-LCR-InformationListIEs-RL-AdditionRspTDD RNSAP-PROTOCOL-IES ::= {
	{ ID id-DL-DPCH-LCR-InformationItem-RL-AdditionRspTDD		CRITICALITY ignore	TYPE DL-DPCH-LCR-InformationItem-RL-AdditionRspTDD  PRESENCE mandatory	}
}

DL-DPCH-LCR-InformationItem-RL-AdditionRspTDD ::= SEQUENCE {
	repetitionPeriod				RepetitionPeriod,
	repetitionLength				RepetitionLength,
	tDD-DPCHOffset					TDD-DPCHOffset,
	dL-TimeslotLCR-Information		DL-TimeslotLCR-Information,
	tSTD-Indicator					TSTD-Indicator,
	iE-Extensions					ProtocolExtensionContainer { {DL-DPCH-LCR-InformationItem-RL-AdditionRspTDD-ExtIEs} } OPTIONAL,
	...
}

DL-DPCH-LCR-InformationItem-RL-AdditionRspTDD-ExtIEs RNSAP-PROTOCOL-EXTENSION ::= {
	...
}

DCH-InformationResponseList-RL-AdditionRspTDD ::= ProtocolIE-Single-Container {{DCH-InformationResponseListIEs-RL-AdditionRspTDD}}

DCH-InformationResponseListIEs-RL-AdditionRspTDD RNSAP-PROTOCOL-IES ::= {
	{ ID id-DCH-InformationResponse   CRITICALITY ignore	TYPE DCH-InformationResponse  PRESENCE mandatory }
}

DSCH-LCR-InformationResponse-RL-AdditionRspTDD ::= ProtocolIE-Single-Container {{DSCH-LCR-InformationList-RL-AdditionRspTDD}}

DSCH-LCR-InformationList-RL-AdditionRspTDD RNSAP-PROTOCOL-IES ::= {
	{ ID id-DSCH-LCR-InformationListIEs-RL-AdditionRspTDD		CRITICALITY ignore	TYPE DSCH-LCR-InformationListIEs-RL-AdditionRspTDD PRESENCE mandatory }
}

DSCH-LCR-InformationListIEs-RL-AdditionRspTDD ::= SEQUENCE (SIZE(0..maxNoOfDSCHsLCR)) OF DSCH-LCR-InformationItem-RL-AdditionRspTDD

DSCH-LCR-InformationItem-RL-AdditionRspTDD ::= SEQUENCE {
	dsch-ID					DSCH-ID,
	dSCH-FlowControlInformation		DSCH-FlowControlInformation,
	bindingID				BindingID	OPTIONAL,
	transportLayerAddress	TransportLayerAddress	OPTIONAL,
	transportFormatManagement	TransportFormatManagement,
	iE-Extensions			ProtocolExtensionContainer { {DSCH-LCR-InformationItem-RL-AdditionRspTDD-ExtIEs} } OPTIONAL,
	...
}

DSCH-LCR-InformationItem-RL-AdditionRspTDD-ExtIEs RNSAP-PROTOCOL-EXTENSION ::= {
	...
}

USCH-LCR-InformationResponse-RL-AdditionRspTDD ::= ProtocolIE-Single-Container {{USCH-LCR-InformationList-RL-AdditionRspTDD}}

USCH-LCR-InformationList-RL-AdditionRspTDD RNSAP-PROTOCOL-IES ::= {
	{ ID id-USCH-LCR-InformationListIEs-RL-AdditionRspTDD		CRITICALITY ignore	TYPE USCH-LCR-InformationListIEs-RL-AdditionRspTDD PRESENCE mandatory }
}

USCH-LCR-InformationListIEs-RL-AdditionRspTDD ::= SEQUENCE (SIZE(0..maxNoOfUSCHsLCR)) OF USCH-LCR-InformationItem-RL-AdditionRspTDD

USCH-LCR-InformationItem-RL-AdditionRspTDD ::= SEQUENCE {
	usch-ID						USCH-ID,
	transportFormatManagement	TransportFormatManagement,
	diversityIndication			DiversityIndication-RL-AdditionRspTDD2		OPTIONAL,
	iE-Extensions				ProtocolExtensionContainer { {USCH-LCR-InformationItem-RL-AdditionRspTDD-ExtIEs} } OPTIONAL,
	...
}

USCH-LCR-InformationItem-RL-AdditionRspTDD-ExtIEs RNSAP-PROTOCOL-EXTENSION ::= {
	...
}

RL-InformationResponse-RL-AdditionRspTDD768 ::= SEQUENCE {
	rL-ID								RL-ID,
	uRA-Information						URA-Information		OPTIONAL,
	sAI									SAI,
	gA-Cell								GA-Cell		OPTIONAL,
	gA-AccessPointPosition				GA-AccessPointPosition	OPTIONAL,
	ul-TimeSlot-ISCP-Info				UL-TimeSlot-ISCP-Info,
	minUL-SIR							UL-SIR,
	maxUL-SIR							UL-SIR,
	maximumAllowedULTxPower				MaximumAllowedULTxPower,
	maximumDLTxPower					DL-Power,
	minimumDLTxPower					DL-Power,
	pCCPCH-Power						PCCPCH-Power,
	timingAdvanceApplied				TimingAdvanceApplied,
	alphaValue							AlphaValue,
	ul-PhysCH-SF-Variation				UL-PhysCH-SF-Variation,
	synchronisationConfiguration		SynchronisationConfiguration,
	secondary-CCPCH-Info-TDD768			Secondary-CCPCH-Info-TDD768						OPTIONAL,
	ul-CCTrCHInformation768				UL-CCTrCHInformationList-RL-AdditionRspTDD768		OPTIONAL,
	dl-CCTrCHInformation768				DL-CCTrCHInformationList-RL-AdditionRspTDD768		OPTIONAL,
	dCH-Information						DCH-Information-RL-AdditionRspTDD				OPTIONAL,
	dSCH-InformationResponse			DSCH-InformationResponse-RL-AdditionRspTDD		OPTIONAL,
	uSCH-InformationResponse			USCH-InformationResponse-RL-AdditionRspTDD		OPTIONAL,
	neighbouring-UMTS-CellInformation	Neighbouring-UMTS-CellInformation 	OPTIONAL,
	neighbouring-GSM-CellInformation	Neighbouring-GSM-CellInformation OPTIONAL,
	gA-CellAdditionalShapes				GA-CellAdditionalShapes			OPTIONAL,
	hCS-Prio							HCS-Prio						OPTIONAL,
	iE-Extensions						ProtocolExtensionContainer { {RL-InformationResponse-RL-AdditionRspTDD768-ExtIEs} } OPTIONAL,
	...
}

RL-InformationResponse-RL-AdditionRspTDD768-ExtIEs RNSAP-PROTOCOL-EXTENSION ::= {
	{ ID id-Neighbouring-E-UTRA-CellInformation		CRITICALITY ignore	EXTENSION Neighbouring-E-UTRA-CellInformation				PRESENCE optional },
	...
}

UL-CCTrCHInformationList-RL-AdditionRspTDD768 ::= ProtocolIE-Single-Container {{UL-CCTrCHInformationListIEs-RL-AdditionRspTDD768}}

UL-CCTrCHInformationListIEs-RL-AdditionRspTDD768 RNSAP-PROTOCOL-IES ::= {
	{ ID id-UL-CCTrCH-InformationListIE-RL-AdditionRspTDD768   CRITICALITY ignore	TYPE UL-CCTrCHInformationListIE-RL-AdditionRspTDD768		PRESENCE mandatory }
}

UL-CCTrCHInformationListIE-RL-AdditionRspTDD768 ::= SEQUENCE (SIZE (1..maxNrOfCCTrCHs)) OF UL-CCTrCHInformationItem-RL-AdditionRspTDD768

UL-CCTrCHInformationItem-RL-AdditionRspTDD768 ::= SEQUENCE {
	cCTrCH-ID					CCTrCH-ID,
	ul-DPCH-Information768				UL-DPCH-InformationList-RL-AdditionRspTDD768		OPTIONAL,
	iE-Extensions					ProtocolExtensionContainer { {UL-CCTrCHInformationItem-RL-AdditionRspTDD768-ExtIEs} } OPTIONAL,
	...
}

UL-CCTrCHInformationItem-RL-AdditionRspTDD768-ExtIEs RNSAP-PROTOCOL-EXTENSION ::= {
	...
}

UL-DPCH-InformationList-RL-AdditionRspTDD768 ::= ProtocolIE-Single-Container { {UL-DPCH-InformationListIEs-RL-AdditionRspTDD768} }

UL-DPCH-InformationListIEs-RL-AdditionRspTDD768 RNSAP-PROTOCOL-IES ::= {
	{ ID id-UL-DPCH-InformationItem-RL-AdditionRspTDD		CRITICALITY ignore	TYPE UL-DPCH-InformationItem-RL-AdditionRspTDD768  PRESENCE mandatory	}
}

UL-DPCH-InformationItem-RL-AdditionRspTDD768 ::= SEQUENCE {
	repetitionPeriod					RepetitionPeriod,
	repetitionLength					RepetitionLength,
	tDD-DPCHOffset						TDD-DPCHOffset,
	uL-Timeslot-Information768			UL-Timeslot-Information768,
	iE-Extensions						ProtocolExtensionContainer { {UL-DPCH-InformationItem-RL-AdditionRspTDD768-ExtIEs} } OPTIONAL,
	...
}

UL-DPCH-InformationItem-RL-AdditionRspTDD768-ExtIEs RNSAP-PROTOCOL-EXTENSION ::= {
	...
}

DL-CCTrCHInformationList-RL-AdditionRspTDD768 ::= ProtocolIE-Single-Container {{DL-CCTrCHInformationListIEs-RL-AdditionRspTDD768}}

DL-CCTrCHInformationListIEs-RL-AdditionRspTDD768 RNSAP-PROTOCOL-IES ::= {
	{ ID id-DL-CCTrCH-InformationListIE-RL-AdditionRspTDD768   CRITICALITY ignore	TYPE DL-CCTrCHInformationListIE-RL-AdditionRspTDD768		PRESENCE mandatory }
}

DL-CCTrCHInformationListIE-RL-AdditionRspTDD768 ::= SEQUENCE (SIZE (1..maxNrOfCCTrCHs)) OF DL-CCTrCHInformationItem-RL-AdditionRspTDD768

DL-CCTrCHInformationItem-RL-AdditionRspTDD768 ::= SEQUENCE {
	cCTrCH-ID							CCTrCH-ID,
	dl-DPCH-Information768				DL-DPCH-InformationList-RL-AdditionRspTDD768		OPTIONAL,
	cCTrCH-Maximum-DL-Power				DL-Power    OPTIONAL,-- this is a DCH type CCTrCH power
	cCTrCH-Minimum-DL-Power				DL-Power    OPTIONAL, -- this is a DCH type CCTrCH power
	iE-Extensions						ProtocolExtensionContainer { {DL-CCTrCHInformationItem-RL-AdditionRspTDD768-ExtIEs} } OPTIONAL,
	...
}

DL-CCTrCHInformationItem-RL-AdditionRspTDD768-ExtIEs RNSAP-PROTOCOL-EXTENSION ::= {
	...
}

DL-DPCH-InformationList-RL-AdditionRspTDD768 ::= ProtocolIE-Single-Container { {DL-DPCH-InformationListIEs-RL-AdditionRspTDD768} }

DL-DPCH-InformationListIEs-RL-AdditionRspTDD768 RNSAP-PROTOCOL-IES ::= {
	{ ID id-DL-DPCH-InformationItem-RL-AdditionRspTDD768		CRITICALITY ignore	TYPE DL-DPCH-InformationItem-RL-AdditionRspTDD768  PRESENCE mandatory	}
}

DL-DPCH-InformationItem-RL-AdditionRspTDD768 ::= SEQUENCE {
	repetitionPeriod				RepetitionPeriod,
	repetitionLength				RepetitionLength,
	tDD-DPCHOffset					TDD-DPCHOffset,
	dL-Timeslot-Information768		DL-Timeslot-Information768,
	iE-Extensions					ProtocolExtensionContainer { {DL-DPCH-InformationItem-RL-AdditionRspTDD768-ExtIEs} } OPTIONAL,
	...
}

DL-DPCH-InformationItem-RL-AdditionRspTDD768-ExtIEs RNSAP-PROTOCOL-EXTENSION ::= {
	...
}

-- **************************************************************
--
-- RADIO LINK ADDITION FAILURE FDD
--
-- **************************************************************

RadioLinkAdditionFailureFDD ::= SEQUENCE {
	protocolIEs                     ProtocolIE-Container       {{RadioLinkAdditionFailureFDD-IEs}},
	protocolExtensions              ProtocolExtensionContainer {{RadioLinkAdditionFailureFDD-Extensions}}                   OPTIONAL,
	...
}

RadioLinkAdditionFailureFDD-IEs RNSAP-PROTOCOL-IES ::= {
	{ ID id-CauseLevel-RL-AdditionFailureFDD					CRITICALITY		ignore				TYPE CauseLevel-RL-AdditionFailureFDD							PRESENCE	mandatory }|
	{ ID id-CriticalityDiagnostics			CRITICALITY ignore	TYPE CriticalityDiagnostics			PRESENCE optional	},
	...
}

CauseLevel-RL-AdditionFailureFDD ::= CHOICE {
	generalCause		GeneralCauseList-RL-AdditionFailureFDD,
	rLSpecificCause		RLSpecificCauseList-RL-AdditionFailureFDD,
	...
}

GeneralCauseList-RL-AdditionFailureFDD ::= SEQUENCE {
	cause										Cause,
	iE-Extensions								ProtocolExtensionContainer { { GeneralCauseItem-RL-AdditionFailureFDD-ExtIEs} }			OPTIONAL,
	...
}

GeneralCauseItem-RL-AdditionFailureFDD-ExtIEs  RNSAP-PROTOCOL-EXTENSION ::= {
	...
}

RLSpecificCauseList-RL-AdditionFailureFDD ::= SEQUENCE {
	unsuccessful-RL-InformationRespList-RL-AdditionFailureFDD		UnsuccessfulRL-InformationResponseList-RL-AdditionFailureFDD,
	successful-RL-InformationRespList-RL-AdditionFailureFDD			SuccessfulRL-InformationResponseList-RL-AdditionFailureFDD  OPTIONAL,
	iE-Extensions								ProtocolExtensionContainer { { RLSpecificCauseItem-RL-AdditionFailureFDD-ExtIEs} }			OPTIONAL,
	...
}

RLSpecificCauseItem-RL-AdditionFailureFDD-ExtIEs  RNSAP-PROTOCOL-EXTENSION ::= {
	...
}

UnsuccessfulRL-InformationResponseList-RL-AdditionFailureFDD ::= SEQUENCE (SIZE (1..maxNrOfRLs-1)) OF ProtocolIE-Single-Container { {UnsuccessfulRL-InformationResponse-RL-AdditionFailureFDD-IEs} }

UnsuccessfulRL-InformationResponse-RL-AdditionFailureFDD-IEs RNSAP-PROTOCOL-IES ::= {
	{ ID id-UnsuccessfulRL-InformationResponse-RL-AdditionFailureFDD	CRITICALITY ignore	TYPE UnsuccessfulRL-InformationResponse-RL-AdditionFailureFDD		PRESENCE mandatory	}
}

UnsuccessfulRL-InformationResponse-RL-AdditionFailureFDD ::= SEQUENCE {
	rL-ID							RL-ID,
	cause							Cause,
	iE-Extensions					ProtocolExtensionContainer { {UnsuccessfulRL-InformationResponse-RL-AdditionFailureFDD-ExtIEs} } OPTIONAL,
	...
}

UnsuccessfulRL-InformationResponse-RL-AdditionFailureFDD-ExtIEs RNSAP-PROTOCOL-EXTENSION ::= {
	...
}

SuccessfulRL-InformationResponseList-RL-AdditionFailureFDD ::= SEQUENCE (SIZE (0..maxNrOfRLs-2)) OF ProtocolIE-Single-Container { {SuccessfulRL-InformationResponse-RL-AdditionFailureFDD-IEs} }

SuccessfulRL-InformationResponse-RL-AdditionFailureFDD-IEs RNSAP-PROTOCOL-IES ::= {
	{ ID id-SuccessfulRL-InformationResponse-RL-AdditionFailureFDD		CRITICALITY ignore	TYPE SuccessfulRL-InformationResponse-RL-AdditionFailureFDD		PRESENCE mandatory	}
}

SuccessfulRL-InformationResponse-RL-AdditionFailureFDD ::= SEQUENCE {
	rL-ID								RL-ID,
	rL-Set-ID							RL-Set-ID,
	uRA-Information						URA-Information		OPTIONAL,
	sAI									SAI,
	gA-Cell								GA-Cell		OPTIONAL,
	gA-AccessPointPosition				GA-AccessPointPosition		OPTIONAL,
	received-total-wide-band-power		Received-total-wide-band-power,
	not-Used-secondary-CCPCH-Info				NULL		OPTIONAL,
	dl-CodeInformation					DL-CodeInformationList-RL-AdditionFailureFDD,
	diversityIndication					DiversityIndication-RL-AdditionFailureFDD,
	-- This IE represents both the Diversity Indication IE and the choice based on the diversity indication as described in
	-- the tabular message format in subclause 9.1.
	sSDT-SupportIndicator				SSDT-SupportIndicator,
	minUL-SIR							UL-SIR,
	maxUL-SIR							UL-SIR,
	closedlooptimingadjustmentmode		Closedlooptimingadjustmentmode	OPTIONAL,
	maximumAllowedULTxPower				MaximumAllowedULTxPower,
	maximumDLTxPower					DL-Power,
	minimumDLTxPower					DL-Power,
	neighbouring-UMTS-CellInformation	Neighbouring-UMTS-CellInformation OPTIONAL,
	neighbouring-GSM-CellInformation	Neighbouring-GSM-CellInformation OPTIONAL,
	primaryCPICH-Power					PrimaryCPICH-Power,
	pC-Preamble							PC-Preamble,
	sRB-Delay							SRB-Delay,
	iE-Extensions						ProtocolExtensionContainer { {SuccessfulRL-InformationResponse-RL-AdditionFailureFDD-ExtIEs} } OPTIONAL,
	...
}

SuccessfulRL-InformationResponse-RL-AdditionFailureFDD-ExtIEs RNSAP-PROTOCOL-EXTENSION ::= {
	{ ID id-GA-CellAdditionalShapes						CRITICALITY ignore	EXTENSION GA-CellAdditionalShapes							PRESENCE optional }|
	{ ID id-DL-PowerBalancing-ActivationIndicator		CRITICALITY ignore	EXTENSION DL-PowerBalancing-ActivationIndicator		PRESENCE optional }|
	{ ID id-HCS-Prio									CRITICALITY ignore	EXTENSION HCS-Prio												PRESENCE optional }|
	{ ID id-Active-MBMS-Bearer-ServiceFDD-PFL			CRITICALITY ignore	EXTENSION Active-MBMS-Bearer-Service-ListFDD-PFL		PRESENCE optional }|
	{ ID id-EDCH-RLSet-Id								CRITICALITY ignore	EXTENSION RL-Set-ID												PRESENCE optional }|
	{ ID id-EDCH-FDD-DL-ControlChannelInformation		CRITICALITY ignore	EXTENSION EDCH-FDD-DL-ControlChannelInformation		PRESENCE optional }|
	{ ID id-Initial-DL-DPCH-TimingAdjustment			CRITICALITY ignore	EXTENSION DL-DPCH-TimingAdjustment						PRESENCE optional }|
	{ ID id-Neighbouring-E-UTRA-CellInformation			CRITICALITY ignore	EXTENSION Neighbouring-E-UTRA-CellInformation			PRESENCE optional }|
	{ ID id-HSDSCH-PreconfigurationInfo					CRITICALITY ignore	EXTENSION HSDSCH-PreconfigurationInfo					PRESENCE optional }|
	{ ID id-F-DPCH-SlotFormat							CRITICALITY ignore	EXTENSION F-DPCH-SlotFormat									PRESENCE optional }|
	{ ID id-Non-Serving-RL-Preconfig-Info				CRITICALITY ignore	EXTENSION Non-Serving-RL-Preconfig-Info					PRESENCE optional },
	...
}

DL-CodeInformationList-RL-AdditionFailureFDD ::= ProtocolIE-Single-Container {{ DL-CodeInformationListIEs-RL-AdditionFailureFDD }}

DL-CodeInformationListIEs-RL-AdditionFailureFDD RNSAP-PROTOCOL-IES ::= {
	{ ID id-FDD-DL-CodeInformation   CRITICALITY ignore	TYPE FDD-DL-CodeInformation		PRESENCE mandatory }
}

DiversityIndication-RL-AdditionFailureFDD ::= CHOICE {
	combining						Combining-RL-AdditionFailureFDD,
	nonCombining					NonCombining-RL-AdditionFailureFDD
}

Combining-RL-AdditionFailureFDD ::= SEQUENCE {
	rL-ID						RL-ID,
	iE-Extensions				ProtocolExtensionContainer { { CombiningItem-RL-AdditionFailureFDD-ExtIEs} } OPTIONAL,
	...
}

CombiningItem-RL-AdditionFailureFDD-ExtIEs RNSAP-PROTOCOL-EXTENSION ::= {
	{ ID id-DCH-InformationResponse			CRITICALITY ignore	EXTENSION DCH-InformationResponse			PRESENCE optional	}|
	{ ID id-EDCH-FDD-InformationResponse	CRITICALITY ignore	EXTENSION EDCH-FDD-InformationResponse			PRESENCE optional	},
	...
}

NonCombining-RL-AdditionFailureFDD ::= SEQUENCE {
	dCH-InformationResponse		DCH-InformationResponse,
	iE-Extensions								ProtocolExtensionContainer { { NonCombiningItem-RL-AdditionFailureFDD-ExtIEs} } OPTIONAL,
	...
}

NonCombiningItem-RL-AdditionFailureFDD-ExtIEs RNSAP-PROTOCOL-EXTENSION ::= {
	{ ID id-EDCH-FDD-InformationResponse	CRITICALITY ignore	EXTENSION EDCH-FDD-InformationResponse			PRESENCE optional	},
	...
}

RadioLinkAdditionFailureFDD-Extensions RNSAP-PROTOCOL-EXTENSION ::= {
	{ ID id-HS-DSCH-serving-cell-change-informationResponse	CRITICALITY ignore	EXTENSION HS-DSCH-serving-cell-change-informationResponse			PRESENCE optional}|
	{ ID id-E-DCH-Serving-cell-change-informationResponse	CRITICALITY ignore	EXTENSION E-DCH-Serving-cell-change-informationResponse				PRESENCE optional}|
	{ ID id-Additional-HS-Cell-Change-Information-Response	CRITICALITY ignore	EXTENSION Additional-HS-Cell-Change-Information-Response-List				PRESENCE optional}|
	{ ID id-MAChs-ResetIndicator							CRITICALITY ignore	EXTENSION MAChs-ResetIndicator												PRESENCE optional}|
	{ ID id-Additional-EDCH-Cell-Information-Response-RLAdd	CRITICALITY ignore	EXTENSION Additional-EDCH-Cell-Information-Response-RLAddList		PRESENCE optional },
	...
}

-- **************************************************************
--
-- RADIO LINK ADDITION FAILURE TDD
--
-- **************************************************************

RadioLinkAdditionFailureTDD ::= SEQUENCE {
	protocolIEs                     ProtocolIE-Container       {{RadioLinkAdditionFailureTDD-IEs}},
	protocolExtensions              ProtocolExtensionContainer {{RadioLinkAdditionFailureTDD-Extensions}}                   OPTIONAL,
	...
}

RadioLinkAdditionFailureTDD-IEs RNSAP-PROTOCOL-IES ::= {
	{ ID id-CauseLevel-RL-AdditionFailureTDD	CRITICALITY ignore	TYPE CauseLevel-RL-AdditionFailureTDD	PRESENCE mandatory }|
	{ ID id-CriticalityDiagnostics			CRITICALITY ignore	TYPE CriticalityDiagnostics			PRESENCE optional	},
	...
}

CauseLevel-RL-AdditionFailureTDD ::= CHOICE {
	generalCause		GeneralCauseList-RL-AdditionFailureTDD,
	rLSpecificCause		RLSpecificCauseList-RL-AdditionFailureTDD,
	...
}

GeneralCauseList-RL-AdditionFailureTDD ::= SEQUENCE {
	cause						Cause,
	iE-Extensions				ProtocolExtensionContainer { { GeneralCauseItem-RL-AdditionFailureTDD-ExtIEs} }		OPTIONAL,
	...
}

GeneralCauseItem-RL-AdditionFailureTDD-ExtIEs RNSAP-PROTOCOL-EXTENSION ::= {
	...
}

RLSpecificCauseList-RL-AdditionFailureTDD ::= SEQUENCE {
	unsuccessful-RL-InformationRespItem-RL-AdditionFailureTDD	Unsuccessful-RL-InformationRespItem-RL-AdditionFailureTDD,
	iE-Extensions												ProtocolExtensionContainer { { RLSpecificCauseItem-RL-AdditionFailureTDD-ExtIEs} }		OPTIONAL,
	...
}

RLSpecificCauseItem-RL-AdditionFailureTDD-ExtIEs RNSAP-PROTOCOL-EXTENSION ::= {
	...
}

Unsuccessful-RL-InformationRespItem-RL-AdditionFailureTDD ::= ProtocolIE-Single-Container { {Unsuccessful-RL-InformationRespItemIE-RL-AdditionFailureTDD} }

Unsuccessful-RL-InformationRespItemIE-RL-AdditionFailureTDD RNSAP-PROTOCOL-IES ::= {
	{ ID	id-UnsuccessfulRL-InformationResponse-RL-AdditionFailureTDD		CRITICALITY	ignore 		TYPE 	UnsuccessfulRL-InformationResponse-RL-AdditionFailureTDD	PRESENCE mandatory}
}

UnsuccessfulRL-InformationResponse-RL-AdditionFailureTDD ::= SEQUENCE {
	rL-ID						RL-ID,
	cause						Cause,
	iE-Extensions				ProtocolExtensionContainer { {UnsuccessfulRL-InformationResponse-RL-AdditionFailureTDD-ExtIEs} } OPTIONAL,
	...
}

UnsuccessfulRL-InformationResponse-RL-AdditionFailureTDD-ExtIEs RNSAP-PROTOCOL-EXTENSION ::= {
	...
}

RadioLinkAdditionFailureTDD-Extensions RNSAP-PROTOCOL-EXTENSION ::= {
	...
}

-- **************************************************************
--
-- RADIO LINK DELETION REQUEST
--
-- **************************************************************

RadioLinkDeletionRequest ::= SEQUENCE {
	protocolIEs                     ProtocolIE-Container       {{RadioLinkDeletionRequest-IEs}},
	protocolExtensions              ProtocolExtensionContainer {{RadioLinkDeletionRequest-Extensions}}                   OPTIONAL,
	...
}

RadioLinkDeletionRequest-IEs RNSAP-PROTOCOL-IES ::= {
	{ ID id-RL-InformationList-RL-DeletionRqst	CRITICALITY notify	TYPE RL-InformationList-RL-DeletionRqst		PRESENCE mandatory	},
	...
}

RL-InformationList-RL-DeletionRqst			::= SEQUENCE (SIZE (1..maxNrOfRLs)) OF ProtocolIE-Single-Container { {RL-Information-RL-DeletionRqst-IEs} }

RL-Information-RL-DeletionRqst-IEs RNSAP-PROTOCOL-IES ::= {
	{ ID id-RL-Information-RL-DeletionRqst		CRITICALITY notify	TYPE RL-Information-RL-DeletionRqst		PRESENCE mandatory	}
}

RL-Information-RL-DeletionRqst ::= SEQUENCE {
	rL-ID						RL-ID,
	iE-Extensions				ProtocolExtensionContainer { {RL-Information-RL-DeletionRqst-ExtIEs} } OPTIONAL,
	...
}

RL-Information-RL-DeletionRqst-ExtIEs RNSAP-PROTOCOL-EXTENSION ::= {
	...
}

RadioLinkDeletionRequest-Extensions RNSAP-PROTOCOL-EXTENSION ::= {
	...
}

-- **************************************************************
--
-- RADIO LINK DELETION RESPONSE
--
-- **************************************************************

RadioLinkDeletionResponse ::= SEQUENCE {
	protocolIEs                     ProtocolIE-Container       {{RadioLinkDeletionResponse-IEs}},
	protocolExtensions              ProtocolExtensionContainer {{RadioLinkDeletionResponse-Extensions}}                   OPTIONAL,
	...
}

RadioLinkDeletionResponse-IEs RNSAP-PROTOCOL-IES ::= {
	{ ID id-CriticalityDiagnostics			CRITICALITY ignore	TYPE CriticalityDiagnostics			PRESENCE optional	},
	...
}

RadioLinkDeletionResponse-Extensions RNSAP-PROTOCOL-EXTENSION ::= {
	...
}

-- **************************************************************
--
-- RADIO LINK RECONFIGURATION PREPARE FDD
--
-- **************************************************************

RadioLinkReconfigurationPrepareFDD ::= SEQUENCE {
	protocolIEs                     ProtocolIE-Container       {{RadioLinkReconfigurationPrepareFDD-IEs}},
	protocolExtensions              ProtocolExtensionContainer {{RadioLinkReconfigurationPrepareFDD-Extensions}}                   OPTIONAL,
	...
}

RadioLinkReconfigurationPrepareFDD-IEs RNSAP-PROTOCOL-IES ::= {
	{ ID id-AllowedQueuingTime			CRITICALITY reject	TYPE AllowedQueuingTime				PRESENCE optional	} |
	{ ID id-UL-DPCH-Information-RL-ReconfPrepFDD			CRITICALITY reject	TYPE UL-DPCH-Information-RL-ReconfPrepFDD			PRESENCE optional	} |
	{ ID id-DL-DPCH-Information-RL-ReconfPrepFDD			CRITICALITY reject	TYPE DL-DPCH-Information-RL-ReconfPrepFDD			PRESENCE optional	} |
	{ ID id-FDD-DCHs-to-Modify		CRITICALITY reject	TYPE FDD-DCHs-to-Modify		PRESENCE optional	} |
	{ ID id-DCHs-to-Add-FDD		CRITICALITY reject	TYPE DCH-FDD-Information		PRESENCE optional	} |
	{ ID id-DCH-DeleteList-RL-ReconfPrepFDD		CRITICALITY reject	TYPE DCH-DeleteList-RL-ReconfPrepFDD		PRESENCE optional	} |
	{ ID id-RL-InformationList-RL-ReconfPrepFDD	CRITICALITY reject	TYPE RL-InformationList-RL-ReconfPrepFDD	PRESENCE optional	}|
	{ ID id-Transmission-Gap-Pattern-Sequence-Information	CRITICALITY reject	TYPE Transmission-Gap-Pattern-Sequence-Information	 PRESENCE optional },
	...
}

UL-DPCH-Information-RL-ReconfPrepFDD ::= SEQUENCE {
	ul-ScramblingCode				UL-ScramblingCode		OPTIONAL,
	ul-SIRTarget					UL-SIR					OPTIONAL,
	minUL-ChannelisationCodeLength	MinUL-ChannelisationCodeLength 	OPTIONAL,
	maxNrOfUL-DPDCHs				MaxNrOfUL-DPCHs			OPTIONAL
	-- This IE shall be present if minUL-ChannelisationCodeLength equals to 4 --,
	ul-PunctureLimit				PunctureLimit			OPTIONAL,
	tFCS							TFCS 	OPTIONAL,
	ul-DPCCH-SlotFormat				UL-DPCCH-SlotFormat		OPTIONAL,
	diversityMode					DiversityMode			OPTIONAL,
	not-Used-sSDT-CellIDLength		NULL		OPTIONAL,
	not-Used-s-FieldLength			NULL			OPTIONAL,
	iE-Extensions					ProtocolExtensionContainer { {UL-DPCH-Information-RL-ReconfPrepFDD-ExtIEs} } OPTIONAL,
	...
}

UL-DPCH-Information-RL-ReconfPrepFDD-ExtIEs RNSAP-PROTOCOL-EXTENSION ::= {
	{ ID id-UL-DPDCHIndicatorEDCH	CRITICALITY reject		EXTENSION UL-DPDCHIndicatorEDCH	PRESENCE optional	},
	...
}

DL-DPCH-Information-RL-ReconfPrepFDD ::= SEQUENCE {
	tFCS							TFCS	OPTIONAL,
	dl-DPCH-SlotFormat				DL-DPCH-SlotFormat		OPTIONAL,
	nrOfDLchannelisationcodes		NrOfDLchannelisationcodes	OPTIONAL,
	tFCI-SignallingMode				TFCI-SignallingMode		OPTIONAL,
	tFCI-Presence					TFCI-Presence			OPTIONAL
	-- This IE shall be present if DL DPCH Slot Format IE is from 12 to 16 --,
	multiplexingPosition			MultiplexingPosition		OPTIONAL,
	limitedPowerIncrease			LimitedPowerIncrease		OPTIONAL,
	iE-Extensions					ProtocolExtensionContainer { {DL-DPCH-Information-RL-ReconfPrepFDD-ExtIEs} } OPTIONAL,
	...
}

DL-DPCH-Information-RL-ReconfPrepFDD-ExtIEs RNSAP-PROTOCOL-EXTENSION ::= {
	{ ID id-DL-DPCH-Power-Information-RL-ReconfPrepFDD	CRITICALITY reject	EXTENSION DL-DPCH-Power-Information-RL-ReconfPrepFDD	PRESENCE optional	},
	...
}

DL-DPCH-Power-Information-RL-ReconfPrepFDD ::= SEQUENCE {
	powerOffsetInformation					PowerOffsetInformation-RL-ReconfPrepFDD,
	fdd-TPC-DownlinkStepSize				FDD-TPC-DownlinkStepSize,
	innerLoopDLPCStatus						InnerLoopDLPCStatus,
	iE-Extensions							ProtocolExtensionContainer { { DL-DPCH-Power-Information-RL-ReconfPrepFDD-ExtIEs } }	OPTIONAL,
	...
}

DL-DPCH-Power-Information-RL-ReconfPrepFDD-ExtIEs RNSAP-PROTOCOL-EXTENSION ::= {
	...
}

PowerOffsetInformation-RL-ReconfPrepFDD ::= SEQUENCE {
	pO1-ForTFCI-Bits						PowerOffset,
	pO2-ForTPC-Bits							PowerOffset,
	pO3-ForPilotBits						PowerOffset,
	iE-Extensions							ProtocolExtensionContainer { { PowerOffsetInformation-RL-ReconfPrepFDD-ExtIEs} }	OPTIONAL,
	...
}

PowerOffsetInformation-RL-ReconfPrepFDD-ExtIEs RNSAP-PROTOCOL-EXTENSION ::= {
	...
}

DCH-DeleteList-RL-ReconfPrepFDD				::= SEQUENCE (SIZE (0..maxNrOfDCHs)) OF DCH-DeleteItem-RL-ReconfPrepFDD

DCH-DeleteItem-RL-ReconfPrepFDD ::= SEQUENCE {
	dCH-ID							DCH-ID,
	iE-Extensions					ProtocolExtensionContainer { {DCH-DeleteItem-RL-ReconfPrepFDD-ExtIEs} } OPTIONAL,
	...
}

DCH-DeleteItem-RL-ReconfPrepFDD-ExtIEs RNSAP-PROTOCOL-EXTENSION ::= {
	...
}

RL-InformationList-RL-ReconfPrepFDD			::= SEQUENCE (SIZE (0..maxNrOfRLs)) OF ProtocolIE-Single-Container { {RL-Information-RL-ReconfPrepFDD-IEs} }

RL-Information-RL-ReconfPrepFDD-IEs RNSAP-PROTOCOL-IES ::= {
	{ ID id-RL-Information-RL-ReconfPrepFDD		CRITICALITY reject	TYPE RL-Information-RL-ReconfPrepFDD		PRESENCE mandatory	}
}

RL-Information-RL-ReconfPrepFDD ::= SEQUENCE {
	rL-ID						RL-ID,
	not-Used-sSDT-Indication			NULL		OPTIONAL,
	not-Used-sSDT-CellIdentity			NULL		OPTIONAL,
	transmitDiversityIndicator		TransmitDiversityIndicator		OPTIONAL,
	-- This IE shall be present if Diversity Mode IE is present in UL DPCH Information IE and is not equal to "none"
	iE-Extensions					ProtocolExtensionContainer { {RL-Information-RL-ReconfPrepFDD-ExtIEs} } OPTIONAL,
	...
}

RL-Information-RL-ReconfPrepFDD-ExtIEs RNSAP-PROTOCOL-EXTENSION ::= {
	{ ID id-DLReferencePower					CRITICALITY ignore	EXTENSION DL-Power									PRESENCE optional }|
	{ ID id-RL-Specific-DCH-Info				CRITICALITY ignore	EXTENSION RL-Specific-DCH-Info					PRESENCE optional }|
	{ ID id-DL-DPCH-TimingAdjustment			CRITICALITY reject	EXTENSION DL-DPCH-TimingAdjustment				PRESENCE optional }|
	{ ID id-Phase-Reference-Update-Indicator	CRITICALITY ignore	EXTENSION Phase-Reference-Update-Indicator	PRESENCE optional }|
	{ ID id-RL-Specific-EDCH-Information		CRITICALITY reject	EXTENSION RL-Specific-EDCH-Information 		PRESENCE optional }|
	{ ID id-EDCH-RL-Indication					CRITICALITY reject	EXTENSION EDCH-RL-Indication						PRESENCE optional }|
	{ ID id-HSDSCH-PreconfigurationSetup		CRITICALITY ignore	EXTENSION HSDSCH-PreconfigurationSetup			PRESENCE optional }|
	{ ID id-Non-Serving-RL-Preconfig-Setup		CRITICALITY ignore	EXTENSION Non-Serving-RL-Preconfig-Setup		PRESENCE optional }|
	{ ID id-Non-Serving-RL-Preconfig-Removal	CRITICALITY ignore	EXTENSION Non-Serving-RL-Preconfig-Setup		PRESENCE optional },
	...
}

RadioLinkReconfigurationPrepareFDD-Extensions RNSAP-PROTOCOL-EXTENSION ::= {
	{ ID id-HSDSCH-FDD-Information							CRITICALITY reject	EXTENSION HSDSCH-FDD-Information					PRESENCE optional}|
	{ ID id-HSDSCH-Information-to-Modify					CRITICALITY reject	EXTENSION HSDSCH-Information-to-Modify				PRESENCE optional}|
	{ ID id-HSDSCH-MACdFlows-to-Add							CRITICALITY reject	EXTENSION HSDSCH-MACdFlows-Information				PRESENCE optional}|
	{ ID id-HSDSCH-MACdFlows-to-Delete						CRITICALITY reject	EXTENSION HSDSCH-MACdFlows-to-Delete				PRESENCE optional}|
	{ ID id-HSPDSCH-RL-ID									CRITICALITY reject	EXTENSION RL-ID												PRESENCE optional}|
	{ ID id-EDPCH-Information								CRITICALITY reject	EXTENSION EDPCH-Information-RLReconfPrepare-FDD						PRESENCE optional}|
	{ ID id-EDCH-FDD-Information							CRITICALITY reject	EXTENSION EDCH-FDD-Information						PRESENCE optional}|
	{ ID id-EDCH-FDD-Information-To-Modify					CRITICALITY reject	EXTENSION EDCH-FDD-Information-To-Modify			PRESENCE optional}|
	{ ID id-EDCH-MACdFlows-To-Add							CRITICALITY reject	EXTENSION EDCH-MACdFlows-Information				PRESENCE optional}|
	{ ID id-EDCH-MACdFlows-To-Delete						CRITICALITY reject	EXTENSION EDCH-MACdFlows-To-Delete					PRESENCE optional}|
	{ ID id-Serving-EDCHRL-Id								CRITICALITY reject	EXTENSION EDCH-Serving-RL								PRESENCE optional }|
	{ ID id-F-DPCH-Information-RL-ReconfPrepFDD				CRITICALITY reject	EXTENSION F-DPCH-Information-RL-ReconfPrepFDD	PRESENCE optional}|
	{ ID id-Fast-Reconfiguration-Mode						CRITICALITY ignore	EXTENSION Fast-Reconfiguration-Mode					PRESENCE optional }|
	{ ID id-CPC-Information									CRITICALITY reject	EXTENSION CPC-Information								PRESENCE optional}|
	{ ID id-Additional-HS-Cell-Information-RL-Reconf-Prep	CRITICALITY reject	EXTENSION Additional-HS-Cell-Information-RL-Reconf-Prep		PRESENCE optional}|
	{ ID id-UE-AggregateMaximumBitRate						CRITICALITY ignore	EXTENSION UE-AggregateMaximumBitRate				PRESENCE optional	}|
	{ ID id-Additional-EDCH-Cell-Information-RL-Reconf-Prep	CRITICALITY reject	EXTENSION Additional-EDCH-Cell-Information-RL-Reconf-Prep			PRESENCE optional },
	...
}

Additional-HS-Cell-Information-RL-Reconf-Prep	::= SEQUENCE (SIZE (1..maxNrOfHSDSCH-1)) OF Additional-HS-Cell-Information-RL-Reconf-Prep-ItemIEs

Additional-HS-Cell-Information-RL-Reconf-Prep-ItemIEs	::=SEQUENCE{
	hSPDSCH-RL-ID									RL-ID,
	c-ID											C-ID												OPTIONAL,
	hS-DSCH-FDD-Secondary-Serving-Information		HS-DSCH-FDD-Secondary-Serving-Information			OPTIONAL,
	hS-DSCH-Secondary-Serving-Information-To-Modify	HS-DSCH-Secondary-Serving-Information-To-Modify	OPTIONAL,
	hS-HS-DSCH-Secondary-Serving-Remove				HS-DSCH-Secondary-Serving-Remove	OPTIONAL,
	iE-Extensions					ProtocolExtensionContainer { { Additional-HS-Cell-Information-RL-Reconf-Prep-ItemIEs-ExtIEs} } OPTIONAL,
	...
}

Additional-HS-Cell-Information-RL-Reconf-Prep-ItemIEs-ExtIEs	RNSAP-PROTOCOL-EXTENSION ::= {
	...
}

Additional-EDCH-Cell-Information-RL-Reconf-Prep	::=SEQUENCE{
	setup-Or-ConfigurationChange-Or-Removal-Of-EDCH-On-secondary-UL-Frequency							Setup-Or-ConfigurationChange-Or-Removal-Of-EDCH-On-secondary-UL-Frequency,
	iE-Extensions					ProtocolExtensionContainer { { Additional-EDCH-Cell-Information-RL-Reconf-Prep-ExtIEs} } OPTIONAL,
	...
}

Additional-EDCH-Cell-Information-RL-Reconf-Prep-ExtIEs	RNSAP-PROTOCOL-EXTENSION ::= {
	...
}

F-DPCH-Information-RL-ReconfPrepFDD ::= SEQUENCE {
	powerOffsetInformation			PowerOffsetInformation-F-DPCH-RL-ReconfPrepFDD,
	fdd-dl-TPC-DownlinkStepSize		FDD-TPC-DownlinkStepSize,
	limitedPowerIncrease			LimitedPowerIncrease,
	innerLoopDLPCStatus				InnerLoopDLPCStatus,
	iE-Extensions					ProtocolExtensionContainer { { F-DPCH-Information-RL-ReconfPrepFDD-ExtIEs} }					OPTIONAL,
	...
}

F-DPCH-Information-RL-ReconfPrepFDD-ExtIEs RNSAP-PROTOCOL-EXTENSION ::= {
	{ ID id-F-DPCH-SlotFormatSupportRequest		CRITICALITY reject			EXTENSION F-DPCH-SlotFormatSupportRequest		PRESENCE optional	}|
	{ ID id-F-DPCH-SlotFormat				CRITICALITY ignore	EXTENSION F-DPCH-SlotFormat		PRESENCE optional},
	...
}

PowerOffsetInformation-F-DPCH-RL-ReconfPrepFDD ::= SEQUENCE {
	po2-ForTPC-Bits					PowerOffset,
	--This IE shall be ignored by DRNS
	iE-Extensions					ProtocolExtensionContainer { { PowerOffsetInformation-F-DPCH-RL-ReconfPrepFDD-ExtIEs} }		OPTIONAL,
	...
}

PowerOffsetInformation-F-DPCH-RL-ReconfPrepFDD-ExtIEs RNSAP-PROTOCOL-EXTENSION ::= {
	...
}


-- **************************************************************
--
-- RADIO LINK RECONFIGURATION PREPARE TDD
--
-- **************************************************************

RadioLinkReconfigurationPrepareTDD ::= SEQUENCE {
	protocolIEs                     ProtocolIE-Container       {{RadioLinkReconfigurationPrepareTDD-IEs}},
	protocolExtensions              ProtocolExtensionContainer {{RadioLinkReconfigurationPrepareTDD-Extensions}}                   OPTIONAL,
	...
}

RadioLinkReconfigurationPrepareTDD-IEs RNSAP-PROTOCOL-IES ::= {
	{ ID id-AllowedQueuingTime			CRITICALITY reject	TYPE AllowedQueuingTime				PRESENCE optional	} |
	{ ID id-UL-CCTrCH-InformationAddList-RL-ReconfPrepTDD	CRITICALITY notify	TYPE UL-CCTrCH-InformationAddList-RL-ReconfPrepTDD	PRESENCE optional	} |
	{ ID id-UL-CCTrCH-InformationModifyList-RL-ReconfPrepTDD	CRITICALITY notify	TYPE UL-CCTrCH-InformationModifyList-RL-ReconfPrepTDD	PRESENCE optional	} |
	{ ID id-UL-CCTrCH-InformationDeleteList-RL-ReconfPrepTDD	CRITICALITY notify	TYPE UL-CCTrCH-InformationDeleteList-RL-ReconfPrepTDD	PRESENCE optional	} |
	{ ID id-DL-CCTrCH-InformationAddList-RL-ReconfPrepTDD	CRITICALITY notify	TYPE DL-CCTrCH-InformationAddList-RL-ReconfPrepTDD	PRESENCE optional	} |
	{ ID id-DL-CCTrCH-InformationModifyList-RL-ReconfPrepTDD	CRITICALITY notify	TYPE DL-CCTrCH-InformationModifyList-RL-ReconfPrepTDD	PRESENCE optional	} |
	{ ID id-DL-CCTrCH-InformationDeleteList-RL-ReconfPrepTDD	CRITICALITY notify	TYPE DL-CCTrCH-InformationDeleteList-RL-ReconfPrepTDD	PRESENCE optional	} |
	{ ID id-TDD-DCHs-to-Modify		CRITICALITY reject	TYPE TDD-DCHs-to-Modify		PRESENCE optional	} |
	{ ID id-DCHs-to-Add-TDD		CRITICALITY reject	TYPE DCH-TDD-Information		PRESENCE optional	} |
	{ ID id-DCH-DeleteList-RL-ReconfPrepTDD		CRITICALITY reject	TYPE DCH-DeleteList-RL-ReconfPrepTDD		PRESENCE optional	}|
	{ ID id-DSCH-ModifyList-RL-ReconfPrepTDD	CRITICALITY reject	TYPE DSCH-ModifyList-RL-ReconfPrepTDD		PRESENCE optional	} |
	{ ID id-DSCHs-to-Add-TDD		CRITICALITY reject	TYPE DSCH-TDD-Information			PRESENCE optional	} |
	{ ID id-DSCH-DeleteList-RL-ReconfPrepTDD	CRITICALITY reject	TYPE DSCH-DeleteList-RL-ReconfPrepTDD		PRESENCE optional	} |
	{ ID id-USCH-ModifyList-RL-ReconfPrepTDD	CRITICALITY reject	TYPE USCH-ModifyList-RL-ReconfPrepTDD		PRESENCE optional	} |
	{ ID id-USCHs-to-Add		CRITICALITY reject	TYPE USCH-Information			PRESENCE optional	} |
	{ ID id-USCH-DeleteList-RL-ReconfPrepTDD	CRITICALITY reject	TYPE USCH-DeleteList-RL-ReconfPrepTDD		PRESENCE optional	},
	...
}

UL-CCTrCH-InformationAddList-RL-ReconfPrepTDD		::= SEQUENCE (SIZE (0..maxNrOfCCTrCHs)) OF ProtocolIE-Single-Container { {UL-CCTrCH-AddInformation-RL-ReconfPrepTDD-IEs} }

UL-CCTrCH-AddInformation-RL-ReconfPrepTDD-IEs RNSAP-PROTOCOL-IES ::= {
	{ ID id-UL-CCTrCH-AddInformation-RL-ReconfPrepTDD	CRITICALITY notify	TYPE UL-CCTrCH-AddInformation-RL-ReconfPrepTDD	PRESENCE mandatory	}
}

UL-CCTrCH-AddInformation-RL-ReconfPrepTDD ::= SEQUENCE {
	cCTrCH-ID					CCTrCH-ID,
	tFCS						TFCS,
	tFCI-Coding					TFCI-Coding,
	punctureLimit					PunctureLimit,
	iE-Extensions					ProtocolExtensionContainer { {UL-CCTrCH-AddInformation-RL-ReconfPrepTDD-ExtIEs} } OPTIONAL,
	...
}

UL-CCTrCH-AddInformation-RL-ReconfPrepTDD-ExtIEs RNSAP-PROTOCOL-EXTENSION ::= {
	{ ID id-UL-SIRTarget		CRITICALITY reject		EXTENSION		UL-SIR		PRESENCE optional}|
	-- This IE shall be mandatory for 1.28Mcps TDD, not applicable for 3.84Mcps TDD or 7.68Mcps TDD.
{ ID id-TDD-TPC-UplinkStepSize-InformationAdd-LCR-RL-ReconfPrepTDD	CRITICALITY reject	EXTENSION TDD-TPC-UplinkStepSize-LCR	PRESENCE optional	},
	-- Mandatory for 1.28Mcps TDD, not applicable to 3.84Mcps TDD or 7.68Mcps TDD
	...
}

UL-CCTrCH-InformationModifyList-RL-ReconfPrepTDD		::= SEQUENCE (SIZE (0..maxNrOfCCTrCHs)) OF ProtocolIE-Single-Container { {UL-CCTrCH-ModifyInformation-RL-ReconfPrepTDD-IEs} }

UL-CCTrCH-ModifyInformation-RL-ReconfPrepTDD-IEs RNSAP-PROTOCOL-IES ::= {
	{ ID id-UL-CCTrCH-ModifyInformation-RL-ReconfPrepTDD	CRITICALITY notify	TYPE UL-CCTrCH-ModifyInformation-RL-ReconfPrepTDD	PRESENCE mandatory	}
}

UL-CCTrCH-ModifyInformation-RL-ReconfPrepTDD ::= SEQUENCE {
	cCTrCH-ID					CCTrCH-ID,
	tFCS						TFCS		OPTIONAL,
	tFCI-Coding					TFCI-Coding				OPTIONAL,
	punctureLimit					PunctureLimit				OPTIONAL,
	iE-Extensions					ProtocolExtensionContainer { {UL-CCTrCH-ModifyInformation-RL-ReconfPrepTDD-ExtIEs} } OPTIONAL,
	...
}

UL-CCTrCH-ModifyInformation-RL-ReconfPrepTDD-ExtIEs RNSAP-PROTOCOL-EXTENSION ::= {
	{ ID id-UL-SIRTarget		CRITICALITY reject		EXTENSION		UL-SIR		PRESENCE optional}|
	-- This IE shall be applicable for 1.28Mcps TDD only.
{ ID id-TDD-TPC-UplinkStepSize-InformationModify-LCR-RL-ReconfPrepTDD	CRITICALITY reject	EXTENSION	TDD-TPC-UplinkStepSize-LCR		PRESENCE optional	},
	-- Applicable to 1.28Mcps TDD only
	...
}

UL-CCTrCH-InformationDeleteList-RL-ReconfPrepTDD		::= SEQUENCE (SIZE (0..maxNrOfCCTrCHs)) OF ProtocolIE-Single-Container { {UL-CCTrCH-DeleteInformation-RL-ReconfPrepTDD-IEs} }

UL-CCTrCH-DeleteInformation-RL-ReconfPrepTDD-IEs RNSAP-PROTOCOL-IES ::= {
	{ ID id-UL-CCTrCH-DeleteInformation-RL-ReconfPrepTDD	CRITICALITY notify	TYPE UL-CCTrCH-DeleteInformation-RL-ReconfPrepTDD	PRESENCE mandatory	}
}

UL-CCTrCH-DeleteInformation-RL-ReconfPrepTDD ::= SEQUENCE {
	cCTrCH-ID					CCTrCH-ID,
	iE-Extensions					ProtocolExtensionContainer { {UL-CCTrCH-DeleteInformation-RL-ReconfPrepTDD-ExtIEs} } OPTIONAL,
	...
}

UL-CCTrCH-DeleteInformation-RL-ReconfPrepTDD-ExtIEs RNSAP-PROTOCOL-EXTENSION ::= {
	...
}

DL-CCTrCH-InformationAddList-RL-ReconfPrepTDD		::= SEQUENCE (SIZE (0..maxNrOfCCTrCHs)) OF ProtocolIE-Single-Container { {DL-CCTrCH-AddInformation-RL-ReconfPrepTDD-IEs} }

DL-CCTrCH-AddInformation-RL-ReconfPrepTDD-IEs RNSAP-PROTOCOL-IES ::= {
	{ ID id-DL-CCTrCH-InformationAddItem-RL-ReconfPrepTDD	CRITICALITY notify	TYPE DL-CCTrCH-InformationAddItem-RL-ReconfPrepTDD	PRESENCE mandatory	}
}

DL-CCTrCH-InformationAddItem-RL-ReconfPrepTDD ::= SEQUENCE {
	cCTrCH-ID					CCTrCH-ID,
	tFCS						TFCS,
	tFCI-Coding					TFCI-Coding,
	punctureLimit					PunctureLimit,
	cCTrCH-TPCList					CCTrCH-TPCAddList-RL-ReconfPrepTDD	OPTIONAL,
	iE-Extensions					ProtocolExtensionContainer { {DL-CCTrCH-InformationAddItem-RL-ReconfPrepTDD-ExtIEs} } OPTIONAL,
	...
}

DL-CCTrCH-InformationAddItem-RL-ReconfPrepTDD-ExtIEs RNSAP-PROTOCOL-EXTENSION ::= {
{ ID id-TDD-TPC-DownlinkStepSize-InformationAdd-RL-ReconfPrepTDD	CRITICALITY reject	EXTENSION	TDD-TPC-DownlinkStepSize	PRESENCE optional	},
	...
}

CCTrCH-TPCAddList-RL-ReconfPrepTDD ::= SEQUENCE (SIZE (1..maxNrOfCCTrCHs)) OF CCTrCH-TPCAddItem-RL-ReconfPrepTDD

CCTrCH-TPCAddItem-RL-ReconfPrepTDD	 ::= SEQUENCE {
	cCTrCH-ID						CCTrCH-ID,
	iE-Extensions					ProtocolExtensionContainer { { CCTrCH-TPCAddItem-RL-ReconfPrepTDD-ExtIEs} } OPTIONAL,
	...
}

CCTrCH-TPCAddItem-RL-ReconfPrepTDD-ExtIEs RNSAP-PROTOCOL-EXTENSION ::= {
	...
}

DL-CCTrCH-InformationModifyList-RL-ReconfPrepTDD		::= SEQUENCE (SIZE (0..maxNrOfCCTrCHs)) OF ProtocolIE-Single-Container { {DL-CCTrCH-ModifyInformation-RL-ReconfPrepTDD-IEs} }

DL-CCTrCH-ModifyInformation-RL-ReconfPrepTDD-IEs RNSAP-PROTOCOL-IES ::= {
	{ ID id-DL-CCTrCH-InformationModifyItem-RL-ReconfPrepTDD	CRITICALITY notify	TYPE DL-CCTrCH-InformationModifyItem-RL-ReconfPrepTDD	PRESENCE mandatory	}
}

DL-CCTrCH-InformationModifyItem-RL-ReconfPrepTDD ::= SEQUENCE {
	cCTrCH-ID					CCTrCH-ID,
	tFCS						TFCS		OPTIONAL,
	tFCI-Coding					TFCI-Coding				OPTIONAL,
	punctureLimit					PunctureLimit				OPTIONAL,
	cCTrCH-TPCList					CCTrCH-TPCModifyList-RL-ReconfPrepTDD		OPTIONAL,
	iE-Extensions					ProtocolExtensionContainer { {DL-CCTrCH-InformationModifyItem-RL-ReconfPrepTDD-ExtIEs} } OPTIONAL,
	...
}

DL-CCTrCH-InformationModifyItem-RL-ReconfPrepTDD-ExtIEs RNSAP-PROTOCOL-EXTENSION ::= {
{ ID id-TDD-TPC-DownlinkStepSize-InformationModify-RL-ReconfPrepTDD	CRITICALITY reject		EXTENSION	TDD-TPC-DownlinkStepSize	PRESENCE optional},
	...
}

CCTrCH-TPCModifyList-RL-ReconfPrepTDD ::= SEQUENCE (SIZE (1..maxNrOfCCTrCHs)) OF CCTrCH-TPCModifyItem-RL-ReconfPrepTDD

CCTrCH-TPCModifyItem-RL-ReconfPrepTDD	 ::= SEQUENCE {
	cCTrCH-ID						CCTrCH-ID,
	iE-Extensions					ProtocolExtensionContainer { { CCTrCH-TPCModifyItem-RL-ReconfPrepTDD-ExtIEs} } OPTIONAL,
	...
}

CCTrCH-TPCModifyItem-RL-ReconfPrepTDD-ExtIEs RNSAP-PROTOCOL-EXTENSION ::= {
	...
}

DL-CCTrCH-InformationDeleteList-RL-ReconfPrepTDD		::= SEQUENCE (SIZE (0..maxNrOfCCTrCHs)) OF ProtocolIE-Single-Container { {DL-CCTrCH-DeleteInformation-RL-ReconfPrepTDD-IEs} }

DL-CCTrCH-DeleteInformation-RL-ReconfPrepTDD-IEs RNSAP-PROTOCOL-IES ::= {
	{ ID id-DL-CCTrCH-InformationDeleteItem-RL-ReconfPrepTDD	CRITICALITY notify	TYPE DL-CCTrCH-InformationDeleteItem-RL-ReconfPrepTDD	PRESENCE mandatory	}
}

DL-CCTrCH-InformationDeleteItem-RL-ReconfPrepTDD ::= SEQUENCE {
	cCTrCH-ID					CCTrCH-ID,
	iE-Extensions					ProtocolExtensionContainer { {DL-CCTrCH-InformationDeleteItem-RL-ReconfPrepTDD-ExtIEs} } OPTIONAL,
	...
}

DL-CCTrCH-InformationDeleteItem-RL-ReconfPrepTDD-ExtIEs RNSAP-PROTOCOL-EXTENSION ::= {
	...
}

DCH-DeleteList-RL-ReconfPrepTDD				::= SEQUENCE (SIZE (0..maxNrOfDCHs)) OF DCH-DeleteItem-RL-ReconfPrepTDD

DCH-DeleteItem-RL-ReconfPrepTDD ::= SEQUENCE {
	dCH-ID						DCH-ID,
	iE-Extensions				ProtocolExtensionContainer { {DCH-DeleteItem-RL-ReconfPrepTDD-ExtIEs} } OPTIONAL,
	...
}

DCH-DeleteItem-RL-ReconfPrepTDD-ExtIEs RNSAP-PROTOCOL-EXTENSION ::= {
	...
}

DSCH-ModifyList-RL-ReconfPrepTDD ::= SEQUENCE (SIZE(0..maxNoOfDSCHs)) OF DSCH-ModifyItem-RL-ReconfPrepTDD

DSCH-ModifyItem-RL-ReconfPrepTDD ::= SEQUENCE {
	dSCH-ID								DSCH-ID,
	dl-ccTrCHID							CCTrCH-ID						OPTIONAL,
	trChSourceStatisticsDescriptor		TrCH-SrcStatisticsDescr	OPTIONAL,
	transportFormatSet					TransportFormatSet				OPTIONAL,
	allocationRetentionPriority 		AllocationRetentionPriority		OPTIONAL,
	schedulingPriorityIndicator			SchedulingPriorityIndicator		OPTIONAL,
	bLER								BLER							OPTIONAL,
	transportBearerRequestIndicator		TransportBearerRequestIndicator,
	iE-Extensions					ProtocolExtensionContainer { {DSCH-ModifyItem-RL-ReconfPrepTDD-ExtIEs} } OPTIONAL,
	...
}

DSCH-ModifyItem-RL-ReconfPrepTDD-ExtIEs RNSAP-PROTOCOL-EXTENSION ::= {
	{ ID id-TrafficClass					CRITICALITY ignore	EXTENSION TrafficClass							PRESENCE optional	}|
	{ ID id-BindingID						CRITICALITY	ignore		EXTENSION 	BindingID			PRESENCE 	optional	}|
	-- Shall be ignored if bearer establishment with ALCAP.
	{ ID id-TransportLayerAddress			CRITICALITY	ignore		EXTENSION 	TransportLayerAddress		PRESENCE optional	}|
	-- Shall be ignored if bearer establishment with ALCAP.
	{ ID id-TnlQos							CRITICALITY ignore		EXTENSION	TnlQos							PRESENCE optional	},
	-- Shall be ignored if bearer establishment with ALCAP.
	...
}

DSCH-DeleteList-RL-ReconfPrepTDD ::= SEQUENCE (SIZE(0..maxNoOfDSCHs)) OF DSCH-DeleteItem-RL-ReconfPrepTDD

DSCH-DeleteItem-RL-ReconfPrepTDD ::= SEQUENCE {
	dSCH-ID								DSCH-ID,
	iE-Extensions					ProtocolExtensionContainer { {DSCH-DeleteItem-RL-ReconfPrepTDD-ExtIEs} } OPTIONAL,
	...
}

DSCH-DeleteItem-RL-ReconfPrepTDD-ExtIEs RNSAP-PROTOCOL-EXTENSION ::= {
	...
}

USCH-ModifyList-RL-ReconfPrepTDD ::= SEQUENCE (SIZE(0..maxNoOfUSCHs)) OF USCH-ModifyItem-RL-ReconfPrepTDD

USCH-ModifyItem-RL-ReconfPrepTDD ::= SEQUENCE {
	uSCH-ID								USCH-ID,
	ul-ccTrCHID							CCTrCH-ID						OPTIONAL,
	trChSourceStatisticsDescriptor		TrCH-SrcStatisticsDescr	OPTIONAL,
	transportFormatSet					TransportFormatSet				OPTIONAL,
	allocationRetentionPriority 		AllocationRetentionPriority		OPTIONAL,
	schedulingPriorityIndicator			SchedulingPriorityIndicator		OPTIONAL,
	bLER								BLER							OPTIONAL,
	transportBearerRequestIndicator		TransportBearerRequestIndicator,
	rb-Info								RB-Info							OPTIONAL,
	iE-Extensions						ProtocolExtensionContainer { {USCH-ModifyItem-RL-ReconfPrepTDD-ExtIEs} } OPTIONAL,
	...
}

USCH-ModifyItem-RL-ReconfPrepTDD-ExtIEs RNSAP-PROTOCOL-EXTENSION ::= {
	{ ID id-TrafficClass			CRITICALITY ignore	EXTENSION TrafficClass				PRESENCE optional	}|
	{ ID id-BindingID				CRITICALITY	ignore	EXTENSION 	BindingID	PRESENCE 		optional	}|
	-- Shall be ignored if bearer establishment with ALCAP.
	{ ID id-TransportLayerAddress			CRITICALITY	ignore		EXTENSION 	TransportLayerAddress		PRESENCE 	optional	}|
	-- Shall be ignored if bearer establishment with ALCAP.
	{ ID id-TnlQos						CRITICALITY 	ignore		EXTENSION 	TnlQos		PRESENCE 		optional	},
	...
}

USCH-DeleteList-RL-ReconfPrepTDD ::= SEQUENCE (SIZE(0..maxNoOfUSCHs)) OF USCH-DeleteItem-RL-ReconfPrepTDD

USCH-DeleteItem-RL-ReconfPrepTDD ::= SEQUENCE {
	uSCH-ID								USCH-ID,
	iE-Extensions					ProtocolExtensionContainer { {USCH-DeleteItem-RL-ReconfPrepTDD-ExtIEs} } OPTIONAL,
	...
}

USCH-DeleteItem-RL-ReconfPrepTDD-ExtIEs RNSAP-PROTOCOL-EXTENSION ::= {
	...
}

RadioLinkReconfigurationPrepareTDD-Extensions RNSAP-PROTOCOL-EXTENSION ::= {
	{ ID id-PrimaryCCPCH-RSCP-RL-ReconfPrepTDD					CRITICALITY ignore	EXTENSION PrimaryCCPCH-RSCP			PRESENCE optional	}|
	{ ID id-DL-TimeSlot-ISCP-Info-RL-ReconfPrepTDD				CRITICALITY ignore	EXTENSION DL-TimeSlot-ISCP-Info		PRESENCE optional	}|
	{ ID id-DL-Timeslot-ISCP-LCR-Information-RL-ReconfPrepTDD	CRITICALITY ignore	EXTENSION DL-TimeSlot-ISCP-LCR-Information	PRESENCE optional	}|
	{ ID id-HSDSCH-TDD-Information								CRITICALITY reject	EXTENSION HSDSCH-TDD-Information	PRESENCE optional}|
	{ ID id-HSDSCH-Information-to-Modify						CRITICALITY reject	EXTENSION HSDSCH-Information-to-Modify		PRESENCE optional}|
	{ ID id-HSDSCH-MACdFlows-to-Add				CRITICALITY reject		EXTENSION HSDSCH-MACdFlows-Information		PRESENCE optional}|
	{ ID id-HSDSCH-MACdFlows-to-Delete			CRITICALITY reject		EXTENSION HSDSCH-MACdFlows-to-Delete		PRESENCE optional}|
	{ ID id-HSPDSCH-RL-ID						CRITICALITY reject		EXTENSION RL-ID											PRESENCE optional}|
	{ ID id-PDSCH-RL-ID							CRITICALITY ignore		EXTENSION RL-ID											PRESENCE optional }|
	{ ID id-UL-Synchronisation-Parameters-LCR	CRITICALITY	ignore		EXTENSION UL-Synchronisation-Parameters-LCR		PRESENCE optional	}|
-- Mandatory for 1.28Mcps TDD, Not Applicable to 3.84Mcps TDD or 7.68Mcps TDD
	{ ID id-RL-Information-RL-ReconfPrepTDD		CRITICALITY	ignore		EXTENSION RL-Information-RL-ReconfPrepTDD		PRESENCE optional	}|
	{ ID id-PrimaryCCPCH-RSCP-Delta				CRITICALITY	ignore		EXTENSION PrimaryCCPCH-RSCP-Delta					PRESENCE optional	}|
	{ ID id-E-DCH-Information-Reconfig			CRITICALITY reject		EXTENSION E-DCH-Information-Reconfig		PRESENCE optional	}|
	{ ID id-E-DCH-Serving-RL-ID					CRITICALITY reject		EXTENSION RL-ID					PRESENCE optional	}|
	{ ID id-E-DCH-768-Information-Reconfig		CRITICALITY reject		EXTENSION E-DCH-768-Information-Reconfig		PRESENCE optional	}|
	{ ID id-E-DCH-LCR-Information-Reconfig		CRITICALITY reject		EXTENSION E-DCH-LCR-Information-Reconfig			PRESENCE optional	}|
	{ ID id-NeedforIdleInterval					CRITICALITY ignore		EXTENSION	NeedforIdleInterval						PRESENCE optional }|
	{ ID id-CPC-InformationLCR					CRITICALITY reject		EXTENSION CPC-InformationLCR							PRESENCE optional }|
	{ ID id-RNTI-Allocation-Indicator			CRITICALITY ignore		EXTENSION  RNTI-Allocation-Indicator				PRESENCE optional }|
	{ ID id-DCH-MeasurementType-Indicator		CRITICALITY reject		EXTENSION DCH-MeasurementType-Indicator		PRESENCE optional},
	...
}


RL-Information-RL-ReconfPrepTDD ::= SEQUENCE (SIZE (1..maxNrOfRLs)) OF RL-InformationIE-RL-ReconfPrepTDD

RL-InformationIE-RL-ReconfPrepTDD ::= SEQUENCE {
	rL-ID								RL-ID,
	rL-Specific-DCH-Info				RL-Specific-DCH-Info			OPTIONAL,
	iE-Extensions						ProtocolExtensionContainer { { RL-InformationIE-RL-ReconfPrepTDD-ExtIEs} }		OPTIONAL,
	...
}

RL-InformationIE-RL-ReconfPrepTDD-ExtIEs RNSAP-PROTOCOL-EXTENSION ::= {
	...
}

-- **************************************************************
--
-- RADIO LINK RECONFIGURATION READY FDD
--
-- **************************************************************

RadioLinkReconfigurationReadyFDD ::= SEQUENCE {
	protocolIEs                     ProtocolIE-Container       {{RadioLinkReconfigurationReadyFDD-IEs}},
	protocolExtensions              ProtocolExtensionContainer {{RadioLinkReconfigurationReadyFDD-Extensions}}                   OPTIONAL,
	...
}

RadioLinkReconfigurationReadyFDD-IEs RNSAP-PROTOCOL-IES ::= {
	{ ID id-RL-InformationResponseList-RL-ReconfReadyFDD	CRITICALITY ignore	TYPE RL-InformationResponseList-RL-ReconfReadyFDD		PRESENCE optional	} |
	{ ID id-CriticalityDiagnostics			CRITICALITY ignore	TYPE CriticalityDiagnostics			PRESENCE optional	},
	...
}

RL-InformationResponseList-RL-ReconfReadyFDD		::= SEQUENCE (SIZE (0..maxNrOfRLs)) OF ProtocolIE-Single-Container { {RL-InformationResponse-RL-ReconfReadyFDD-IEs} }

RL-InformationResponse-RL-ReconfReadyFDD-IEs RNSAP-PROTOCOL-IES ::= {
	{ ID id-RL-InformationResponseItem-RL-ReconfReadyFDD	CRITICALITY ignore	TYPE RL-InformationResponseItem-RL-ReconfReadyFDD		PRESENCE mandatory	}
}

RL-InformationResponseItem-RL-ReconfReadyFDD ::= SEQUENCE {
	rL-ID	RL-ID,
	max-UL-SIR	UL-SIR	OPTIONAL,
	min-UL-SIR	UL-SIR	OPTIONAL,
	maximumDLTxPower	DL-Power	OPTIONAL,
	minimumDLTxPower	DL-Power	OPTIONAL,
	not-Used-secondary-CCPCH-Info	NULL	OPTIONAL,
	dl-CodeInformationList	DL-CodeInformationList-RL-ReconfReadyFDD	OPTIONAL,
	dCHInformationResponse	DCH-InformationResponseList-RL-ReconfReadyFDD	OPTIONAL,
	not-Used-dSCHsToBeAddedOrModified	NULL	OPTIONAL,
	iE-Extensions	ProtocolExtensionContainer { {RL-InformationResponseItem-RL-ReconfReadyFDD-ExtIEs} }	OPTIONAL,
	...
}

RL-InformationResponseItem-RL-ReconfReadyFDD-ExtIEs RNSAP-PROTOCOL-EXTENSION ::= {
	{ ID id-DL-PowerBalancing-UpdatedIndicator			CRITICALITY ignore	EXTENSION DL-PowerBalancing-UpdatedIndicator				PRESENCE optional }|
	{ ID id-Primary-CPICH-Usage-For-Channel-Estimation	CRITICALITY ignore	EXTENSION Primary-CPICH-Usage-For-Channel-Estimation	PRESENCE optional }|
	{ ID id-Secondary-CPICH-Information-Change			CRITICALITY ignore	EXTENSION Secondary-CPICH-Information-Change				PRESENCE optional }|
	{ ID id-EDCH-FDD-InformationResponse				CRITICALITY ignore	EXTENSION EDCH-FDD-InformationResponse						PRESENCE optional }|
	{ ID id-EDCH-RLSet-Id								CRITICALITY ignore	EXTENSION RL-Set-ID													PRESENCE optional }|
	{ ID id-EDCH-FDD-DL-ControlChannelInformation		CRITICALITY ignore	EXTENSION EDCH-FDD-DL-ControlChannelInformation			PRESENCE optional }|
	{ ID id-F-DPCH-SlotFormat							CRITICALITY ignore	EXTENSION F-DPCH-SlotFormat										PRESENCE optional }|
	{ ID id-HSDSCH-PreconfigurationInfo					CRITICALITY ignore	EXTENSION HSDSCH-PreconfigurationInfo						PRESENCE optional }|
	{ ID id-Non-Serving-RL-Preconfig-Info				CRITICALITY ignore	EXTENSION Non-Serving-RL-Preconfig-Info						PRESENCE optional },
...
}

DL-CodeInformationList-RL-ReconfReadyFDD ::= ProtocolIE-Single-Container {{ DL-CodeInformationListIEs-RL-ReconfReadyFDD }}

DL-CodeInformationListIEs-RL-ReconfReadyFDD RNSAP-PROTOCOL-IES ::= {
	{ ID id-FDD-DL-CodeInformation   CRITICALITY ignore	TYPE FDD-DL-CodeInformation		PRESENCE mandatory }
}

DCH-InformationResponseList-RL-ReconfReadyFDD				::= ProtocolIE-Single-Container { {DCH-InformationResponseListIEs-RL-ReconfReadyFDD} }

DCH-InformationResponseListIEs-RL-ReconfReadyFDD RNSAP-PROTOCOL-IES ::= {
	{ ID id-DCH-InformationResponse		CRITICALITY ignore	TYPE DCH-InformationResponse		PRESENCE mandatory	}
}

RadioLinkReconfigurationReadyFDD-Extensions RNSAP-PROTOCOL-EXTENSION ::= {
	{ ID id-HSDSCH-RNTI							CRITICALITY ignore		EXTENSION HSDSCH-RNTI									PRESENCE optional }|
	{ ID id-HSDSCH-FDD-Information-Response		CRITICALITY ignore		EXTENSION HSDSCH-FDD-Information-Response		PRESENCE optional }|
	{ ID id-MAChs-ResetIndicator				CRITICALITY ignore		EXTENSION MAChs-ResetIndicator						PRESENCE optional }|
	{ ID id-Fast-Reconfiguration-Permission		CRITICALITY ignore		EXTENSION Fast-Reconfiguration-Permission		PRESENCE optional }|
	{ ID id-Continuous-Packet-Connectivity-HS-SCCH-Less-Information-Response		CRITICALITY ignore		EXTENSION Continuous-Packet-Connectivity-HS-SCCH-Less-Information-Response		PRESENCE optional }|
	{ ID id-Additional-HS-Cell-RL-Reconf-Response	CRITICALITY ignore		EXTENSION Additional-HS-Cell-RL-Reconf-Response		PRESENCE optional }|
	{ ID id-Additional-EDCH-Cell-Information-ResponseRLReconf		CRITICALITY ignore	EXTENSION	Additional-EDCH-Cell-Information-Response-RLReconf-List			PRESENCE optional },
	...
}


Additional-HS-Cell-RL-Reconf-Response	::= SEQUENCE (SIZE (1..maxNrOfHSDSCH-1)) OF Additional-HS-Cell-RL-Reconf-Response-ItemIEs

Additional-HS-Cell-RL-Reconf-Response-ItemIEs	::=SEQUENCE{
	hSPDSCH-RL-ID										RL-ID,
	hSDSCH-RNTI											HSDSCH-RNTI,
	hS-DSCH-FDD-Secondary-Serving-Information-Response	HS-DSCH-FDD-Secondary-Serving-Information-Response,
	iE-Extensions					ProtocolExtensionContainer { { Additional-HS-Cell-RL-Reconf-Response-ItemIEs-ExtIEs} } OPTIONAL,
	...
}

Additional-HS-Cell-RL-Reconf-Response-ItemIEs-ExtIEs	RNSAP-PROTOCOL-EXTENSION ::= {
	...
}

-- **************************************************************
--
-- RADIO LINK RECONFIGURATION READY TDD
--
-- **************************************************************

RadioLinkReconfigurationReadyTDD ::= SEQUENCE {
	protocolIEs                     ProtocolIE-Container       {{RadioLinkReconfigurationReadyTDD-IEs}},
	protocolExtensions              ProtocolExtensionContainer {{RadioLinkReconfigurationReadyTDD-Extensions}}                   OPTIONAL,
	...
}

RadioLinkReconfigurationReadyTDD-IEs RNSAP-PROTOCOL-IES ::= {
	{ ID id-RL-InformationResponse-RL-ReconfReadyTDD
							CRITICALITY ignore	TYPE RL-InformationResponse-RL-ReconfReadyTDD	PRESENCE optional	} |
	--This RL-InformationResponse-RL-ReconfReadyTDD is for the first RL repetition in the list.
	--Repetitions 2 and on are defined in Multiple-RL-InformationResponse-RL-ReconfReadyTDD.
	{ ID id-CriticalityDiagnostics			CRITICALITY ignore	TYPE CriticalityDiagnostics			PRESENCE optional	},
	...
}

RL-InformationResponse-RL-ReconfReadyTDD ::= SEQUENCE {
	rL-ID							RL-ID,
	max-UL-SIR						UL-SIR			OPTIONAL,
	min-UL-SIR						UL-SIR			OPTIONAL,
	maximumDLTxPower				DL-Power		OPTIONAL,
	minimumDLTxPower				DL-Power		OPTIONAL,
	secondary-CCPCH-Info-TDD		Secondary-CCPCH-Info-TDD	OPTIONAL,
	ul-CCTrCH-Information			UL-CCTrCH-InformationList-RL-ReconfReadyTDD 	OPTIONAL,
	dl-CCTrCH-Information			DL-CCTrCH-InformationList-RL-ReconfReadyTDD	OPTIONAL,
	dCHInformationResponse			DCH-InformationResponseList-RL-ReconfReadyTDD	OPTIONAL,
	dSCHsToBeAddedOrModified		DSCHToBeAddedOrModified-RL-ReconfReadyTDD	OPTIONAL,
	uSCHsToBeAddedOrModified		USCHToBeAddedOrModified-RL-ReconfReadyTDD	OPTIONAL,
	iE-Extensions					ProtocolExtensionContainer { {RL-InformationResponse-RL-ReconfReadyTDD-ExtIEs} }	OPTIONAL,
	...
}

RL-InformationResponse-RL-ReconfReadyTDD-ExtIEs RNSAP-PROTOCOL-EXTENSION ::= {
	{ ID id-UL-TimingAdvanceCtrl-LCR						CRITICALITY ignore	EXTENSION UL-TimingAdvanceCtrl-LCR				PRESENCE optional }|
	--For 1.28Mcps TDD only
	{ ID id-secondary-LCR-CCPCH-Info-TDD					CRITICALITY ignore	EXTENSION Secondary-LCR-CCPCH-Info-TDD			PRESENCE optional }|
	--For 1.28Mcps TDD only
	{ ID id-secondary-CCPCH-Info-RL-ReconfReadyTDD768		CRITICALITY ignore	EXTENSION Secondary-CCPCH-Info-TDD768			PRESENCE optional }|
	{ ID id-UARFCNforNt										CRITICALITY ignore	EXTENSION UARFCN				PRESENCE optional },
	-- Applicable to 1.28Mcps TDD only
	...
}

UL-CCTrCH-InformationList-RL-ReconfReadyTDD 		::= ProtocolIE-Single-Container {{UL-CCTrCHInformationListIEs-RL-ReconfReadyTDD}}

UL-CCTrCHInformationListIEs-RL-ReconfReadyTDD RNSAP-PROTOCOL-IES ::= {
	{ ID id-UL-CCTrCH-InformationListIE-RL-ReconfReadyTDD   CRITICALITY ignore	TYPE UL-CCTrCHInformationListIE-RL-ReconfReadyTDD		PRESENCE mandatory }
}

UL-CCTrCHInformationListIE-RL-ReconfReadyTDD ::= SEQUENCE (SIZE (0..maxNrOfCCTrCHs)) OF UL-CCTrCH-InformationItem-RL-ReconfReadyTDD

UL-CCTrCH-InformationItem-RL-ReconfReadyTDD ::= SEQUENCE {
	cCTrCH-ID						CCTrCH-ID,
	ul-DPCH-AddInformation			UL-DPCH-InformationAddList-RL-ReconfReadyTDD			OPTIONAL,
	--For 3.84Mcps TDD only
	ul-DPCH-ModifyInformation		UL-DPCH-InformationModifyList-RL-ReconfReadyTDD				OPTIONAL,
	ul-DPCH-DeleteInformation		UL-DPCH-InformationDeleteList-RL-ReconfReadyTDD				OPTIONAL,
	iE-Extensions					ProtocolExtensionContainer { {UL-CCTrCH-InformationItem-RL-ReconfReadyTDD-ExtIEs} } OPTIONAL,
	...
}

UL-CCTrCH-InformationItem-RL-ReconfReadyTDD-ExtIEs RNSAP-PROTOCOL-EXTENSION ::= {
	{ ID id-UL-DPCH-LCR-InformationAddListIE-RL-ReconfReadyTDD		CRITICALITY ignore		EXTENSION UL-DPCH-LCR-InformationAddList-RL-ReconfReadyTDD		PRESENCE optional }|
	--For 1.28Mcps TDD only
	{ ID id-UL-DPCH-InformationAddListIE-RL-ReconfReadyTDD768		CRITICALITY ignore		EXTENSION UL-DPCH-InformationAddList-RL-ReconfReadyTDD768		PRESENCE optional },
	--For 7.68Mcps TDD only
	...
}

UL-DPCH-LCR-InformationAddList-RL-ReconfReadyTDD ::= SEQUENCE {
	repetitionPeriod				RepetitionPeriod,
	repetitionLength				RepetitionLength,
	tDD-DPCHOffset					TDD-DPCHOffset,
	uL-TimeslotLCR-Info				UL-TimeslotLCR-Information,
	iE-Extensions					ProtocolExtensionContainer { {UL-DPCH-LCR-InformationAddItem-RL-ReconfReadyTDD-ExtIEs} } OPTIONAL,
	...
}

UL-DPCH-LCR-InformationAddItem-RL-ReconfReadyTDD-ExtIEs RNSAP-PROTOCOL-EXTENSION ::= {
	...
}

UL-DPCH-InformationAddList-RL-ReconfReadyTDD ::= ProtocolIE-Single-Container {{UL-DPCH-InformationAddListIEs-RL-ReconfReadyTDD}}

UL-DPCH-InformationAddListIEs-RL-ReconfReadyTDD RNSAP-PROTOCOL-IES ::= {
	{ ID id-UL-DPCH-InformationAddListIE-RL-ReconfReadyTDD   CRITICALITY ignore	TYPE UL-DPCH-InformationAddListIE-RL-ReconfReadyTDD		PRESENCE optional }
}

UL-DPCH-InformationAddListIE-RL-ReconfReadyTDD ::= SEQUENCE {
	repetitionPeriod				RepetitionPeriod,
	repetitionLength				RepetitionLength,
	tDD-DPCHOffset					TDD-DPCHOffset,
	rxTimingDeviationForTA			RxTimingDeviationForTA			OPTIONAL,
	uL-Timeslot-Information			UL-Timeslot-Information,
	iE-Extensions					ProtocolExtensionContainer { {UL-DPCH-InformationAddItem-RL-ReconfReadyTDD-ExtIEs} } OPTIONAL,
	...
}

UL-DPCH-InformationAddItem-RL-ReconfReadyTDD-ExtIEs RNSAP-PROTOCOL-EXTENSION ::= {
	{ ID id-RxTimingDeviationForTAext		CRITICALITY ignore		EXTENSION RxTimingDeviationForTAext		PRESENCE optional },
	...
}

UL-DPCH-InformationAddList-RL-ReconfReadyTDD768 ::= SEQUENCE {
	repetitionPeriod				RepetitionPeriod,
	repetitionLength				RepetitionLength,
	tDD-DPCHOffset					TDD-DPCHOffset,
	rxTimingDeviationForTA768			RxTimingDeviationForTA768			OPTIONAL,
	uL-Timeslot-Information768			UL-Timeslot-Information768,
	iE-Extensions					ProtocolExtensionContainer { {UL-DPCH-InformationAddItem-RL-ReconfReadyTDD768-ExtIEs} } OPTIONAL,
	...
}

UL-DPCH-InformationAddItem-RL-ReconfReadyTDD768-ExtIEs RNSAP-PROTOCOL-EXTENSION ::= {
	...
}

UL-DPCH-InformationModifyList-RL-ReconfReadyTDD ::= ProtocolIE-Single-Container {{UL-DPCH-InformationModifyListIEs-RL-ReconfReadyTDD}}

UL-DPCH-InformationModifyListIEs-RL-ReconfReadyTDD RNSAP-PROTOCOL-IES ::= {
	{ ID id-UL-DPCH-InformationModifyListIE-RL-ReconfReadyTDD   CRITICALITY ignore	TYPE UL-DPCH-InformationModifyListIE-RL-ReconfReadyTDD		PRESENCE mandatory }
}

UL-DPCH-InformationModifyListIE-RL-ReconfReadyTDD::= SEQUENCE {
	repetitionPeriod				RepetitionPeriod			OPTIONAL,
	repetitionLength				RepetitionLength			OPTIONAL,
	tDD-DPCHOffset					TDD-DPCHOffset				OPTIONAL,
	uL-Timeslot-InformationModifyList-RL-ReconfReadyTDD			UL-Timeslot-InformationModifyList-RL-ReconfReadyTDD			OPTIONAL,
	--For 3.84Mcps TDD only
	iE-Extensions					ProtocolExtensionContainer { {UL-DPCH-InformationModifyItem-RL-ReconfReadyTDD-ExtIEs} } OPTIONAL,
	...
}

UL-DPCH-InformationModifyItem-RL-ReconfReadyTDD-ExtIEs RNSAP-PROTOCOL-EXTENSION ::= {
	{ ID id-UL-Timeslot-LCR-InformationModifyList-RL-ReconfReadyTDD   CRITICALITY ignore	EXTENSION  UL-TimeslotLCR-InformationModifyList-RL-ReconfReadyTDD		PRESENCE optional }|
	--For 1.28Mcps TDD only
	{ ID id-UL-Timeslot-InformationModifyList-RL-ReconfReadyTDD768   CRITICALITY ignore	EXTENSION  UL-Timeslot-InformationModifyList-RL-ReconfReadyTDD768		PRESENCE optional },
	--For 7.68Mcps TDD only
...
}

UL-TimeslotLCR-InformationModifyList-RL-ReconfReadyTDD::= SEQUENCE ( SIZE (1..maxNrOfTsLCR)) OF UL-TimeslotLCR-InformationModifyItem-RL-ReconfReadyTDD

UL-TimeslotLCR-InformationModifyItem-RL-ReconfReadyTDD ::= SEQUENCE {
	timeSlotLCR						TimeSlotLCR,
	midambleShiftLCR				MidambleShiftLCR			OPTIONAL,
	tFCI-Presence					TFCI-Presence			OPTIONAL,
	tDD-uL-Code-LCR-Information			TDD-UL-Code-LCR-InformationModifyList-RL-ReconfReadyTDD			OPTIONAL,
	iE-Extensions					ProtocolExtensionContainer { {UL-TimeslotLCR-InformationModifyItem-RL-ReconfReadyTDD-ExtIEs} } OPTIONAL,
	...
}

TDD-UL-Code-LCR-InformationModifyList-RL-ReconfReadyTDD::= SEQUENCE ( SIZE (1..maxNrOfDPCHsLCR)) OF TDD-UL-Code-LCR-InformationModifyItem-RL-ReconfReadyTDD

TDD-UL-Code-LCR-InformationModifyItem-RL-ReconfReadyTDD ::= SEQUENCE {
	dPCH-ID							DPCH-ID,
	tDD-ChannelisationCodeLCR			TDD-ChannelisationCodeLCR		OPTIONAL,
	iE-Extensions					ProtocolExtensionContainer { {TDD-UL-Code-LCR-InformationModifyItem-RL-ReconfReadyTDD-ExtIEs} } OPTIONAL,
	...
}

TDD-UL-Code-LCR-InformationModifyItem-RL-ReconfReadyTDD-ExtIEs RNSAP-PROTOCOL-EXTENSION ::= {
{ ID id-TDD-UL-DPCH-TimeSlotFormatModifyItem-LCR-RL-ReconfReadyTDD	 CRITICALITY	reject	 EXTENSION TDD-UL-DPCH-TimeSlotFormat-LCR   PRESENCE  optional},
	...
}

UL-TimeslotLCR-InformationModifyItem-RL-ReconfReadyTDD-ExtIEs RNSAP-PROTOCOL-EXTENSION ::= {
	...
}

UL-Timeslot-InformationModifyList-RL-ReconfReadyTDD::= SEQUENCE ( SIZE (1..maxNrOfTS)) OF UL-Timeslot-InformationModifyItem-RL-ReconfReadyTDD

UL-Timeslot-InformationModifyItem-RL-ReconfReadyTDD ::= SEQUENCE {
	timeSlot						TimeSlot,
	midambleShiftAndBurstType					MidambleShiftAndBurstType			OPTIONAL,
	tFCI-Presence					TFCI-Presence			OPTIONAL,
	uL-Code-Information			TDD-UL-Code-InformationModifyList-RL-ReconfReadyTDD			OPTIONAL,
	iE-Extensions					ProtocolExtensionContainer { {UL-Timeslot-InformationModifyItem-RL-ReconfReadyTDD-ExtIEs} } OPTIONAL,
	...
}

UL-Timeslot-InformationModifyItem-RL-ReconfReadyTDD-ExtIEs RNSAP-PROTOCOL-EXTENSION ::= {
	...
}

TDD-UL-Code-InformationModifyList-RL-ReconfReadyTDD::= SEQUENCE ( SIZE (1..maxNrOfDPCHs)) OF TDD-UL-Code-InformationModifyItem-RL-ReconfReadyTDD

TDD-UL-Code-InformationModifyItem-RL-ReconfReadyTDD ::= SEQUENCE {
	dPCH-ID							DPCH-ID,
	tDD-ChannelisationCode			TDD-ChannelisationCode		OPTIONAL,
	iE-Extensions					ProtocolExtensionContainer { {TDD-UL-Code-InformationModifyItem-RL-ReconfReadyTDD-ExtIEs} } OPTIONAL,
	...
}

TDD-UL-Code-InformationModifyItem-RL-ReconfReadyTDD-ExtIEs RNSAP-PROTOCOL-EXTENSION ::= {
	...
}

UL-Timeslot-InformationModifyList-RL-ReconfReadyTDD768::= SEQUENCE ( SIZE (1..maxNrOfTS)) OF UL-Timeslot-InformationModifyItem-RL-ReconfReadyTDD768

UL-Timeslot-InformationModifyItem-RL-ReconfReadyTDD768 ::= SEQUENCE {
	timeSlot						TimeSlot,
	midambleShiftAndBurstType768	MidambleShiftAndBurstType768			OPTIONAL,
	tFCI-Presence					TFCI-Presence			OPTIONAL,
	uL-Code-Information768			TDD-UL-Code-InformationModifyList-RL-ReconfReadyTDD768		OPTIONAL,
	iE-Extensions					ProtocolExtensionContainer { {UL-Timeslot-InformationModifyItem-RL-ReconfReadyTDD768-ExtIEs} } OPTIONAL,
	...
}

UL-Timeslot-InformationModifyItem-RL-ReconfReadyTDD768-ExtIEs RNSAP-PROTOCOL-EXTENSION ::= {
	...
}

TDD-UL-Code-InformationModifyList-RL-ReconfReadyTDD768::= SEQUENCE ( SIZE (1..maxNrOfDPCHs768)) OF TDD-UL-Code-InformationModifyItem-RL-ReconfReadyTDD768

TDD-UL-Code-InformationModifyItem-RL-ReconfReadyTDD768 ::= SEQUENCE {
	dPCH-ID							DPCH-ID,
	tDD-ChannelisationCode768		TDD-ChannelisationCode768		OPTIONAL,
	iE-Extensions					ProtocolExtensionContainer { {TDD-UL-Code-InformationModifyItem-RL-ReconfReadyTDD768-ExtIEs} } OPTIONAL,
	...
}

TDD-UL-Code-InformationModifyItem-RL-ReconfReadyTDD768-ExtIEs RNSAP-PROTOCOL-EXTENSION ::= {
	...
}


UL-DPCH-InformationDeleteList-RL-ReconfReadyTDD ::= ProtocolIE-Single-Container {{UL-DPCH-InformationDeleteListIEs-RL-ReconfReadyTDD}}

UL-DPCH-InformationDeleteListIEs-RL-ReconfReadyTDD RNSAP-PROTOCOL-IES ::= {
	{ ID id-UL-DPCH-InformationDeleteListIE-RL-ReconfReadyTDD   CRITICALITY ignore	TYPE UL-DPCH-InformationDeleteListIE-RL-ReconfReadyTDD		PRESENCE mandatory }
}

UL-DPCH-InformationDeleteListIE-RL-ReconfReadyTDD ::= SEQUENCE (SIZE (0..maxNrOfDPCHs)) OF UL-DPCH-InformationDeleteItem-RL-ReconfReadyTDD

UL-DPCH-InformationDeleteItem-RL-ReconfReadyTDD ::= SEQUENCE {
	dPCH-ID						DPCH-ID,
	iE-Extensions					ProtocolExtensionContainer { {UL-DPCH-InformationDeleteList-RL-ReconfReadyTDD-ExtIEs} } OPTIONAL,
	...
}

UL-DPCH-InformationDeleteList-RL-ReconfReadyTDD-ExtIEs RNSAP-PROTOCOL-EXTENSION ::= {
	...
}

DL-CCTrCH-InformationList-RL-ReconfReadyTDD 		::= ProtocolIE-Single-Container {{DL-CCTrCHInformationListIEs-RL-ReconfReadyTDD}}

DL-CCTrCHInformationListIEs-RL-ReconfReadyTDD RNSAP-PROTOCOL-IES ::= {
	{ ID id-DL-CCTrCH-InformationListIE-RL-ReconfReadyTDD   CRITICALITY ignore	TYPE DL-CCTrCHInformationListIE-RL-ReconfReadyTDD		PRESENCE mandatory }
}

DL-CCTrCHInformationListIE-RL-ReconfReadyTDD ::= SEQUENCE (SIZE (0..maxNrOfCCTrCHs)) OF DL-CCTrCH-InformationItem-RL-ReconfReadyTDD

DL-CCTrCH-InformationItem-RL-ReconfReadyTDD ::= SEQUENCE {
	cCTrCH-ID						CCTrCH-ID,
	dl-DPCH-AddInformation			DL-DPCH-InformationAddList-RL-ReconfReadyTDD			OPTIONAL,
	--For 3.84Mcps TDD only
	dl-DPCH-ModifyInformation		DL-DPCH-InformationModifyList-RL-ReconfReadyTDD			OPTIONAL,
	dl-DPCH-DeleteInformation		DL-DPCH-InformationDeleteList-RL-ReconfReadyTDD			OPTIONAL,
	iE-Extensions					ProtocolExtensionContainer { {DL-CCTrCH-InformationItem-RL-ReconfReadyTDD-ExtIEs} } OPTIONAL,
	...
}

DL-CCTrCH-InformationItem-RL-ReconfReadyTDD-ExtIEs RNSAP-PROTOCOL-EXTENSION ::= {
	{ ID id-DL-DPCH-LCR-InformationAddListIE-RL-ReconfReadyTDD   CRITICALITY ignore			EXTENSION	 DL-DPCH-LCR-InformationAddList-RL-ReconfReadyTDD		PRESENCE  optional}|
	--For 1.28Mcps TDD only
	{ ID id-CCTrCH-Maximum-DL-Power-RL-ReconfReadyTDD				CRITICALITY ignore		EXTENSION DL-Power						PRESENCE optional	}|
	-- Applicable to 3.84Mcps TDD and 7.68Mcps TDD only, this is a DCH type CCTrCH power
	{ ID id-CCTrCH-Minimum-DL-Power-RL-ReconfReadyTDD				CRITICALITY ignore		EXTENSION DL-Power						PRESENCE optional	}|
	-- Applicable to 3.84Mcps TDD and 7.68Mcps TDD only, this is a DCH type CCTrCH power
	{ ID id-DL-DPCH-InformationAddListIE-RL-ReconfReadyTDD768		CRITICALITY ignore		EXTENSION DL-DPCH-InformationAddList-RL-ReconfReadyTDD768						PRESENCE  optional}|
	--For 7.68Mcps TDD only
	{ ID id-DL-DPCH-InformationDeleteList768-RL-ReconfReadyTDD		CRITICALITY ignore		EXTENSION DL-DPCH-InformationDeleteList768-RL-ReconfReadyTDD		PRESENCE optional},
	...
}

DL-DPCH-LCR-InformationAddList-RL-ReconfReadyTDD ::= SEQUENCE {
	repetitionPeriod				RepetitionPeriod,
	repetitionLength				RepetitionLength,
	tDD-DPCHOffset					TDD-DPCHOffset,
	dL-TimeslotLCR-Info				DL-TimeslotLCR-Information,
	iE-Extensions					ProtocolExtensionContainer { {DL-DPCH-LCR-InformationAddItem-RL-ReconfReadyTDD-ExtIEs} } OPTIONAL,
	...
}

DL-DPCH-LCR-InformationAddItem-RL-ReconfReadyTDD-ExtIEs RNSAP-PROTOCOL-EXTENSION ::= {
	...
}

DL-DPCH-InformationAddList-RL-ReconfReadyTDD ::= ProtocolIE-Single-Container {{DL-DPCH-InformationAddListIEs-RL-ReconfReadyTDD}}

DL-DPCH-InformationAddListIEs-RL-ReconfReadyTDD RNSAP-PROTOCOL-IES ::= {
	{ ID id-DL-DPCH-InformationAddListIE-RL-ReconfReadyTDD   CRITICALITY ignore	TYPE DL-DPCH-InformationAddListIE-RL-ReconfReadyTDD		PRESENCE mandatory }
}

DL-DPCH-InformationAddListIE-RL-ReconfReadyTDD ::= SEQUENCE {
	repetitionPeriod				RepetitionPeriod,
	repetitionLength				RepetitionLength,
	tDD-DPCHOffset					TDD-DPCHOffset,
	dL-Timeslot-Information			DL-Timeslot-Information,
	iE-Extensions					ProtocolExtensionContainer { {DL-DPCH-InformationAddItem-RL-ReconfReadyTDD-ExtIEs} } OPTIONAL,
	...
}

DL-DPCH-InformationAddItem-RL-ReconfReadyTDD-ExtIEs RNSAP-PROTOCOL-EXTENSION ::= {
	...
}

DL-DPCH-InformationAddList-RL-ReconfReadyTDD768 ::= SEQUENCE {
	repetitionPeriod				RepetitionPeriod,
	repetitionLength				RepetitionLength,
	tDD-DPCHOffset					TDD-DPCHOffset,
	dL-Timeslot-Information768		DL-Timeslot-Information768,
	iE-Extensions					ProtocolExtensionContainer { {DL-DPCH-InformationAddItem-RL-ReconfReadyTDD768-ExtIEs} } OPTIONAL,
	...
}

DL-DPCH-InformationAddItem-RL-ReconfReadyTDD768-ExtIEs RNSAP-PROTOCOL-EXTENSION ::= {
	...
}

DL-DPCH-InformationModifyList-RL-ReconfReadyTDD ::= ProtocolIE-Single-Container {{DL-DPCH-InformationModifyListIEs-RL-ReconfReadyTDD}}

DL-DPCH-InformationModifyListIEs-RL-ReconfReadyTDD RNSAP-PROTOCOL-IES ::= {
	{ ID id-DL-DPCH-InformationModifyListIE-RL-ReconfReadyTDD   CRITICALITY ignore	TYPE DL-DPCH-InformationModifyListIE-RL-ReconfReadyTDD		PRESENCE mandatory }
}

DL-DPCH-InformationModifyListIE-RL-ReconfReadyTDD ::= SEQUENCE {
	repetitionPeriod				RepetitionPeriod			OPTIONAL,
	repetitionLength				RepetitionLength			OPTIONAL,
	tDD-DPCHOffset					TDD-DPCHOffset				OPTIONAL,
	dL-Timeslot-InformationModifyList-RL-ReconfReadyTDD			DL-Timeslot-InformationModifyList-RL-ReconfReadyTDD			OPTIONAL,
	--For 3.84Mcps TDD only
	iE-Extensions					ProtocolExtensionContainer { {DL-DPCH-InformationModifyItem-RL-ReconfReadyTDD-ExtIEs} } OPTIONAL,
	...
}

DL-DPCH-InformationModifyItem-RL-ReconfReadyTDD-ExtIEs RNSAP-PROTOCOL-EXTENSION ::= {
	{ ID id-DL-Timeslot-LCR-InformationModifyList-RL-ReconfReadyTDD   CRITICALITY ignore	EXTENSION  DL-TimeslotLCR-InformationModifyList-RL-ReconfReadyTDD		PRESENCE optional }|
	--For 1.28Mcps TDD only
	{ ID id-DL-Timeslot-InformationModifyList-RL-ReconfReadyTDD768   CRITICALITY ignore	EXTENSION  DL-Timeslot-InformationModifyList-RL-ReconfReadyTDD768		PRESENCE optional },
	--For 7.68Mcps TDD only
	...
}

DL-TimeslotLCR-InformationModifyList-RL-ReconfReadyTDD::= SEQUENCE ( SIZE (1..maxNrOfTsLCR)) OF DL-TimeslotLCR-InformationModifyItem-RL-ReconfReadyTDD

DL-TimeslotLCR-InformationModifyItem-RL-ReconfReadyTDD ::= SEQUENCE {
	timeSlotLCR						TimeSlotLCR,
	midambleShiftLCR				MidambleShiftLCR			OPTIONAL,
	tFCI-Presence					TFCI-Presence			OPTIONAL,
	tDD-dL-Code-LCR-Information		TDD-DL-Code-LCR-InformationModifyList-RL-ReconfReadyTDD			OPTIONAL,
	iE-Extensions					ProtocolExtensionContainer { {DL-TimeslotLCR-InformationModifyItem-RL-ReconfReadyTDD-ExtIEs} } OPTIONAL,
	...
}

TDD-DL-Code-LCR-InformationModifyList-RL-ReconfReadyTDD::= SEQUENCE ( SIZE (1..maxNrOfDPCHsLCR)) OF TDD-DL-Code-LCR-InformationModifyItem-RL-ReconfReadyTDD

TDD-DL-Code-LCR-InformationModifyItem-RL-ReconfReadyTDD ::= SEQUENCE {
	dPCH-ID							DPCH-ID,
	tDD-ChannelisationCodeLCR		TDD-ChannelisationCodeLCR		OPTIONAL,
	iE-Extensions					ProtocolExtensionContainer { {TDD-DL-Code-LCR-InformationModifyItem-RL-ReconfReadyTDD-ExtIEs} } OPTIONAL,
	...
}

TDD-DL-Code-LCR-InformationModifyItem-RL-ReconfReadyTDD-ExtIEs RNSAP-PROTOCOL-EXTENSION ::= {
	{ ID id-TDD-DL-DPCH-TimeSlotFormatModifyItem-LCR-RL-ReconfReadyTDD		CRITICALITY reject			EXTENSION TDD-DL-DPCH-TimeSlotFormat-LCR		PRESENCE optional},
	...
}

DL-TimeslotLCR-InformationModifyItem-RL-ReconfReadyTDD-ExtIEs RNSAP-PROTOCOL-EXTENSION ::= {
	{ ID id-Maximum-DL-Power-TimeslotLCR-InformationModifyItem-RL-ReconfReadyTDD   CRITICALITY ignore	EXTENSION   DL-Power		PRESENCE optional }|
	{ ID id-Minimum-DL-Power-TimeslotLCR-InformationModifyItem-RL-ReconfReadyTDD   CRITICALITY ignore	EXTENSION   DL-Power		PRESENCE optional },
	...
}

DL-Timeslot-InformationModifyList-RL-ReconfReadyTDD::= SEQUENCE ( SIZE (1..maxNrOfTS)) OF DL-Timeslot-InformationModifyItem-RL-ReconfReadyTDD

DL-Timeslot-InformationModifyItem-RL-ReconfReadyTDD ::= SEQUENCE {
	timeSlot						TimeSlot,
	midambleShiftAndBurstType		MidambleShiftAndBurstType			OPTIONAL,
	tFCI-Presence					TFCI-Presence			OPTIONAL,
	dL-Code-Information				TDD-DL-Code-InformationModifyList-RL-ReconfReadyTDD			OPTIONAL,
	iE-Extensions					ProtocolExtensionContainer { {DL-Timeslot-InformationModifyItem-RL-ReconfReadyTDD-ExtIEs} } OPTIONAL,
	...
}

DL-Timeslot-InformationModifyItem-RL-ReconfReadyTDD-ExtIEs RNSAP-PROTOCOL-EXTENSION ::= {
	...
}

TDD-DL-Code-InformationModifyList-RL-ReconfReadyTDD::= SEQUENCE ( SIZE (1..maxNrOfDPCHs)) OF TDD-DL-Code-InformationModifyItem-RL-ReconfReadyTDD

TDD-DL-Code-InformationModifyItem-RL-ReconfReadyTDD ::= SEQUENCE {
	dPCH-ID							DPCH-ID,
	tDD-ChannelisationCode			TDD-ChannelisationCode		OPTIONAL,
	iE-Extensions					ProtocolExtensionContainer { {TDD-DL-Code-InformationModifyItem-RL-ReconfReadyTDD-ExtIEs} } OPTIONAL,
	...
}

TDD-DL-Code-InformationModifyItem-RL-ReconfReadyTDD-ExtIEs RNSAP-PROTOCOL-EXTENSION ::= {
	{ ID id-TDD-DL-DPCH-TimeSlotFormatModifyItem-LCR-RL-ReconfReadyTDD	 CRITICALITY	reject	 EXTENSION TDD-DL-DPCH-TimeSlotFormat-LCR   PRESENCE  optional},
	-- This IE shall not be used
	...
}

DL-Timeslot-InformationModifyList-RL-ReconfReadyTDD768::= SEQUENCE ( SIZE (1..maxNrOfTS)) OF DL-Timeslot-InformationModifyItem-RL-ReconfReadyTDD768

DL-Timeslot-InformationModifyItem-RL-ReconfReadyTDD768 ::= SEQUENCE {
	timeSlot						TimeSlot,
	midambleShiftAndBurstType768	MidambleShiftAndBurstType768			OPTIONAL,
	tFCI-Presence					TFCI-Presence			OPTIONAL,
	dL-Code-Information768			TDD-DL-Code-InformationModifyList-RL-ReconfReadyTDD768			OPTIONAL,
	iE-Extensions					ProtocolExtensionContainer { {DL-Timeslot-InformationModifyItem-RL-ReconfReadyTDD768-ExtIEs} } OPTIONAL,
	...
}

DL-Timeslot-InformationModifyItem-RL-ReconfReadyTDD768-ExtIEs RNSAP-PROTOCOL-EXTENSION ::= {
	...
}

TDD-DL-Code-InformationModifyList-RL-ReconfReadyTDD768::= SEQUENCE ( SIZE (1..maxNrOfDPCHs768)) OF TDD-DL-Code-InformationModifyItem-RL-ReconfReadyTDD768

TDD-DL-Code-InformationModifyItem-RL-ReconfReadyTDD768 ::= SEQUENCE {
	dPCH-ID768						DPCH-ID768,
	tDD-ChannelisationCode768		TDD-ChannelisationCode768		OPTIONAL,
	iE-Extensions					ProtocolExtensionContainer { {TDD-DL-Code-InformationModifyItem-RL-ReconfReadyTDD768-ExtIEs} } OPTIONAL,
	...
}

TDD-DL-Code-InformationModifyItem-RL-ReconfReadyTDD768-ExtIEs RNSAP-PROTOCOL-EXTENSION ::= {
	...
}

DL-DPCH-InformationDeleteList-RL-ReconfReadyTDD ::= ProtocolIE-Single-Container {{DL-DPCH-InformationDeleteListIEs-RL-ReconfReadyTDD}}

DL-DPCH-InformationDeleteListIEs-RL-ReconfReadyTDD RNSAP-PROTOCOL-IES ::= {
	{ ID id-DL-DPCH-InformationDeleteListIE-RL-ReconfReadyTDD   CRITICALITY ignore	TYPE DL-DPCH-InformationDeleteListIE-RL-ReconfReadyTDD		PRESENCE mandatory }
}

DL-DPCH-InformationDeleteListIE-RL-ReconfReadyTDD ::= SEQUENCE (SIZE (0..maxNrOfDPCHs)) OF DL-DPCH-InformationDeleteItem-RL-ReconfReadyTDD

DL-DPCH-InformationDeleteItem-RL-ReconfReadyTDD ::= SEQUENCE {
	dPCH-ID						DPCH-ID,
	iE-Extensions					ProtocolExtensionContainer { {DL-DPCH-InformationDeleteList-RL-ReconfReadyTDD-ExtIEs} } OPTIONAL,
	...
}

DL-DPCH-InformationDeleteList-RL-ReconfReadyTDD-ExtIEs RNSAP-PROTOCOL-EXTENSION ::= {
	...
}

DL-DPCH-InformationDeleteList768-RL-ReconfReadyTDD ::= SEQUENCE (SIZE (0..maxNrOfDPCHs768)) OF DL-DPCH-InformationDeleteItem768-RL-ReconfReadyTDD

DL-DPCH-InformationDeleteItem768-RL-ReconfReadyTDD ::= SEQUENCE {
	dPCH-ID768						DPCH-ID768,
	iE-Extensions					ProtocolExtensionContainer { {DL-DPCH-InformationDeleteList768-RL-ReconfReadyTDD-ExtIEs} } OPTIONAL,
	...
}

DL-DPCH-InformationDeleteList768-RL-ReconfReadyTDD-ExtIEs RNSAP-PROTOCOL-EXTENSION ::= {
	...
}

DCH-InformationResponseList-RL-ReconfReadyTDD				::= ProtocolIE-Single-Container { {DCH-InformationResponseListIEs-RL-ReconfReadyTDD} }

DCH-InformationResponseListIEs-RL-ReconfReadyTDD RNSAP-PROTOCOL-IES ::= {
	{ ID id-DCH-InformationResponse		CRITICALITY ignore	TYPE DCH-InformationResponse		PRESENCE mandatory	}
}

DSCHToBeAddedOrModified-RL-ReconfReadyTDD			::= ProtocolIE-Single-Container { {DSCHToBeAddedOrModifiedIEs-RL-ReconfReadyTDD} }

DSCHToBeAddedOrModifiedIEs-RL-ReconfReadyTDD RNSAP-PROTOCOL-IES ::= {
	{ ID id-DSCHToBeAddedOrModifiedList-RL-ReconfReadyTDD	CRITICALITY ignore	TYPE DSCHToBeAddedOrModifiedList-RL-ReconfReadyTDD		PRESENCE mandatory	}
}

DSCHToBeAddedOrModifiedList-RL-ReconfReadyTDD ::= SEQUENCE (SIZE (0..maxNoOfDSCHs)) OF DSCHToBeAddedOrModifiedItem-RL-ReconfReadyTDD

DSCHToBeAddedOrModifiedItem-RL-ReconfReadyTDD ::= SEQUENCE {
	dsch-ID					DSCH-ID,
	transportFormatManagement	TransportFormatManagement,
	dSCH-FlowControlInformation	DSCH-FlowControlInformation,
	bindingID				BindingID	OPTIONAL,
	transportLayerAddress	TransportLayerAddress	OPTIONAL,
	iE-Extensions			ProtocolExtensionContainer { {DSCHToBeAddedOrModifiedItem-RL-ReconfReadyTDD-ExtIEs} } OPTIONAL,
	...
}

DSCHToBeAddedOrModifiedItem-RL-ReconfReadyTDD-ExtIEs RNSAP-PROTOCOL-EXTENSION ::= {
	...
}

USCHToBeAddedOrModified-RL-ReconfReadyTDD			::= ProtocolIE-Single-Container { {USCHToBeAddedOrModifiedIEs-RL-ReconfReadyTDD} }USCHToBeAddedOrModifiedIEs-RL-ReconfReadyTDD RNSAP-PROTOCOL-IES ::= {
	{ ID id-USCHToBeAddedOrModifiedList-RL-ReconfReadyTDD	CRITICALITY ignore	TYPE USCHToBeAddedOrModifiedList-RL-ReconfReadyTDD		PRESENCE mandatory	}
}

USCHToBeAddedOrModifiedList-RL-ReconfReadyTDD ::= SEQUENCE (SIZE (0..maxNoOfUSCHs)) OF USCHToBeAddedOrModifiedItem-RL-ReconfReadyTDD

USCHToBeAddedOrModifiedItem-RL-ReconfReadyTDD ::= SEQUENCE {
	uSCH-ID					USCH-ID,
	transportFormatManagement	TransportFormatManagement,
	bindingID				BindingID	OPTIONAL,
	transportLayerAddress	TransportLayerAddress	OPTIONAL,
	iE-Extensions			ProtocolExtensionContainer { {USCHToBeAddedOrModifiedItem-RL-ReconfReadyTDD-ExtIEs} } OPTIONAL,
	...
}

USCHToBeAddedOrModifiedItem-RL-ReconfReadyTDD-ExtIEs RNSAP-PROTOCOL-EXTENSION ::= {
	...
}

RadioLinkReconfigurationReadyTDD-Extensions RNSAP-PROTOCOL-EXTENSION ::= {
	{ ID id-HSDSCH-RNTI							CRITICALITY ignore		EXTENSION HSDSCH-RNTI									PRESENCE optional }|
	{ ID id-DSCH-RNTI							CRITICALITY ignore		EXTENSION DSCH-RNTI										PRESENCE optional }|
	{ ID id-HSDSCH-TDD-Information-Response		CRITICALITY ignore		EXTENSION HSDSCH-TDD-Information-Response		PRESENCE optional }|
	{ ID id-MAChs-ResetIndicator				CRITICALITY ignore		EXTENSION MAChs-ResetIndicator						PRESENCE optional }|
	{ ID id-Multiple-RL-InformationResponse-RL-ReconfReadyTDD	CRITICALITY	ignore		EXTENSION 	Multiple-RL-InformationResponse-RL-ReconfReadyTDD		PRESENCE 	optional}|
-- This is for RL repetitions 2 and on in RL list.
	{ ID id-E-DCH-Information-Response			CRITICALITY ignore		EXTENSION E-DCH-Information-Response		PRESENCE optional	}|
	{ ID id-E-DCH-768-Information-Response		CRITICALITY ignore		EXTENSION E-DCH-768-Information-Response		PRESENCE optional	}|
	{ ID id-E-DCH-LCR-Information-Response		CRITICALITY ignore		EXTENSION E-DCH-LCR-Information-Response		PRESENCE optional	}|
	{ ID id-PowerControlGAP						CRITICALITY ignore		EXTENSION ControlGAP				PRESENCE optional }|
	-- Applicable to 1.28Mcps TDD only
	{ ID id-IdleIntervalInformation				CRITICALITY ignore		EXTENSION	IdleIntervalInformation		PRESENCE optional }|
	{ ID id-ContinuousPacketConnectivity-DRX-Information-ResponseLCR	CRITICALITY ignore	EXTENSION ContinuousPacketConnectivity-DRX-Information-ResponseLCR			PRESENCE optional	}|
	{ ID id-HS-DSCH-Semi-PersistentScheduling-Information-ResponseLCR	CRITICALITY ignore	EXTENSION HS-DSCH-Semi-PersistentScheduling-Information-ResponseLCR			PRESENCE optional}|
	{ ID id-E-DCH-Semi-PersistentScheduling-Information-ResponseLCR		CRITICALITY ignore	EXTENSION E-DCH-Semi-PersistentScheduling-Information-ResponseLCR			PRESENCE optional}|
	{ ID id-E-RNTI-For-FACH						CRITICALITY ignore		EXTENSION E-RNTI										PRESENCE optional }|
	{ ID id-H-RNTI-For-FACH						CRITICALITY ignore		EXTENSION HSDSCH-RNTI									PRESENCE optional }|
	{ ID id-DCH-MeasurementOccasion-Information		CRITICALITY reject	EXTENSION DCH-MeasurementOccasion-Information	PRESENCE optional },
	...
}

Multiple-RL-InformationResponse-RL-ReconfReadyTDD ::= SEQUENCE (SIZE (1..maxNrOfRLs-1)) OF RL-InformationResponse-RL-ReconfReadyTDD


-- **************************************************************
--
-- RADIO LINK RECONFIGURATION COMMIT
--
-- **************************************************************

RadioLinkReconfigurationCommit ::= SEQUENCE {
	protocolIEs                     ProtocolIE-Container       {{RadioLinkReconfigurationCommit-IEs}},
	protocolExtensions              ProtocolExtensionContainer {{RadioLinkReconfigurationCommit-Extensions}}                   OPTIONAL,
	...
}

RadioLinkReconfigurationCommit-IEs RNSAP-PROTOCOL-IES ::= {
	{ ID id-CFN					CRITICALITY ignore	TYPE CFN					PRESENCE mandatory	}|
	{ ID id-Active-Pattern-Sequence-Information		CRITICALITY ignore	TYPE Active-Pattern-Sequence-Information		 PRESENCE optional  },--FDD only
	...
}

RadioLinkReconfigurationCommit-Extensions RNSAP-PROTOCOL-EXTENSION ::= {
	{ ID id-Fast-Reconfiguration-Mode	CRITICALITY reject	EXTENSION Fast-Reconfiguration-Mode		PRESENCE optional },--FDD only
	...
}

-- **************************************************************
--
-- RADIO LINK RECONFIGURATION FAILURE
--
-- **************************************************************

RadioLinkReconfigurationFailure ::= SEQUENCE {
	protocolIEs                     ProtocolIE-Container       {{RadioLinkReconfigurationFailure-IEs}},
	protocolExtensions              ProtocolExtensionContainer {{RadioLinkReconfigurationFailure-Extensions}}                   OPTIONAL,
	...
}

RadioLinkReconfigurationFailure-IEs RNSAP-PROTOCOL-IES ::= {
	{ ID id-CauseLevel-RL-ReconfFailure		CRITICALITY ignore	TYPE CauseLevel-RL-ReconfFailure	PRESENCE mandatory } |
	{ ID id-CriticalityDiagnostics			CRITICALITY ignore	TYPE CriticalityDiagnostics			PRESENCE optional },
	...
}

CauseLevel-RL-ReconfFailure ::= CHOICE {
	generalCause		GeneralCauseList-RL-ReconfFailure,
	rLSpecificCause		RLSpecificCauseList-RL-ReconfFailure,
	...
}

GeneralCauseList-RL-ReconfFailure ::= SEQUENCE {
	cause										Cause,
	iE-Extensions								ProtocolExtensionContainer { { GeneralCauseItem-RL-ReconfFailure-ExtIEs} }			OPTIONAL,
	...
 }

GeneralCauseItem-RL-ReconfFailure-ExtIEs  RNSAP-PROTOCOL-EXTENSION ::= {
	...
}

RLSpecificCauseList-RL-ReconfFailure ::= SEQUENCE {
	rL-ReconfigurationFailureList-RL-ReconfFailure		RL-ReconfigurationFailureList-RL-ReconfFailure		OPTIONAL,
	iE-Extensions										ProtocolExtensionContainer { { RLSpecificCauseItem-RL-ReconfFailure-ExtIEs} }			OPTIONAL,
	...
 }

RLSpecificCauseItem-RL-ReconfFailure-ExtIEs  RNSAP-PROTOCOL-EXTENSION ::= {
	...
}

RL-ReconfigurationFailureList-RL-ReconfFailure ::= SEQUENCE (SIZE (0..maxNrOfRLs)) OF ProtocolIE-Single-Container { {RL-ReconfigurationFailure-RL-ReconfFailure-IEs} }

RL-ReconfigurationFailure-RL-ReconfFailure-IEs RNSAP-PROTOCOL-IES ::= {
	{ ID id-RL-ReconfigurationFailure-RL-ReconfFail	CRITICALITY ignore	TYPE RL-ReconfigurationFailure-RL-ReconfFail	PRESENCE mandatory	}
}

RL-ReconfigurationFailure-RL-ReconfFail ::= SEQUENCE {
	rL-ID						RL-ID,
	cause						Cause,
	iE-Extensions				ProtocolExtensionContainer { {RL-ReconfigurationFailure-RL-ReconfFailure-ExtIEs} } OPTIONAL,
	...
}

RL-ReconfigurationFailure-RL-ReconfFailure-ExtIEs RNSAP-PROTOCOL-EXTENSION ::= {
	{ ID id-Max-UE-DTX-Cycle		CRITICALITY ignore		EXTENSION Max-UE-DTX-Cycle				PRESENCE conditional },
	-- This IE shall be present if the Cause IE is set to "Continuous Packet Connectivity UE DTX Cycle not Available".
	...
}

RadioLinkReconfigurationFailure-Extensions RNSAP-PROTOCOL-EXTENSION ::= {
	...
}

-- **************************************************************
--
-- RADIO LINK RECONFIGURATION CANCEL
--
-- **************************************************************

RadioLinkReconfigurationCancel ::= SEQUENCE {
	protocolIEs                     ProtocolIE-Container       {{RadioLinkReconfigurationCancel-IEs}},
	protocolExtensions              ProtocolExtensionContainer {{RadioLinkReconfigurationCancel-Extensions}}                   OPTIONAL,
	...
}

RadioLinkReconfigurationCancel-IEs RNSAP-PROTOCOL-IES ::= {
	...
}

RadioLinkReconfigurationCancel-Extensions RNSAP-PROTOCOL-EXTENSION ::= {
	...
}

-- **************************************************************
--
-- RADIO LINK RECONFIGURATION REQUEST FDD
--
-- **************************************************************

RadioLinkReconfigurationRequestFDD ::= SEQUENCE {
	protocolIEs                     ProtocolIE-Container       {{RadioLinkReconfigurationRequestFDD-IEs}},
	protocolExtensions              ProtocolExtensionContainer {{RadioLinkReconfigurationRequestFDD-Extensions}}                   OPTIONAL,
	...
}

RadioLinkReconfigurationRequestFDD-IEs RNSAP-PROTOCOL-IES ::= {
	{ ID id-AllowedQueuingTime								CRITICALITY reject	TYPE AllowedQueuingTime	PRESENCE optional	} |
	{ ID id-UL-DPCH-Information-RL-ReconfRqstFDD			CRITICALITY reject	TYPE UL-DPCH-Information-RL-ReconfRqstFDD	PRESENCE optional	} |
	{ ID id-DL-DPCH-Information-RL-ReconfRqstFDD			CRITICALITY reject	TYPE DL-DPCH-Information-RL-ReconfRqstFDD	PRESENCE optional	} |
	{ ID id-FDD-DCHs-to-Modify								CRITICALITY reject	TYPE FDD-DCHs-to-Modify	PRESENCE optional	} |
	{ ID id-DCHs-to-Add-FDD									CRITICALITY reject	TYPE DCH-FDD-Information	PRESENCE optional	} |
	{ ID id-DCH-DeleteList-RL-ReconfRqstFDD					CRITICALITY reject	TYPE DCH-DeleteList-RL-ReconfRqstFDD	PRESENCE optional	} |
	{ ID id-Transmission-Gap-Pattern-Sequence-Information	CRITICALITY reject	TYPE Transmission-Gap-Pattern-Sequence-Information	PRESENCE optional },
	...
}

UL-DPCH-Information-RL-ReconfRqstFDD ::= SEQUENCE {
	tFCS							TFCS	OPTIONAL,
	iE-Extensions					ProtocolExtensionContainer { {UL-DPCH-Information-RL-ReconfRqstFDD-ExtIEs} } OPTIONAL,
	...
}

UL-DPCH-Information-RL-ReconfRqstFDD-ExtIEs RNSAP-PROTOCOL-EXTENSION ::= {
	{ ID id-UL-DPDCHIndicatorEDCH	CRITICALITY reject		EXTENSION UL-DPDCHIndicatorEDCH		PRESENCE optional },
	...
}

DL-DPCH-Information-RL-ReconfRqstFDD ::= SEQUENCE {
	tFCS							TFCS	OPTIONAL,
	tFCI-SignallingMode				TFCI-SignallingMode	OPTIONAL,
	limitedPowerIncrease			LimitedPowerIncrease	OPTIONAL,
	iE-Extensions					ProtocolExtensionContainer { {DL-DPCH-Information-RL-ReconfRqstFDD-ExtIEs} } OPTIONAL,
	...
}

DL-DPCH-Information-RL-ReconfRqstFDD-ExtIEs RNSAP-PROTOCOL-EXTENSION ::= {
	...
}

DCH-DeleteList-RL-ReconfRqstFDD				::= SEQUENCE (SIZE (0..maxNrOfDCHs)) OF DCH-DeleteItem-RL-ReconfRqstFDD

DCH-DeleteItem-RL-ReconfRqstFDD ::= SEQUENCE {
	dCH-ID							DCH-ID,
	iE-Extensions					ProtocolExtensionContainer { {DCH-DeleteItem-RL-ReconfRqstFDD-ExtIEs} } OPTIONAL,
	...
}

DCH-DeleteItem-RL-ReconfRqstFDD-ExtIEs RNSAP-PROTOCOL-EXTENSION ::= {
	...
}

RadioLinkReconfigurationRequestFDD-Extensions RNSAP-PROTOCOL-EXTENSION ::= {
	{ ID id-RL-ReconfigurationRequestFDD-RL-InformationList	CRITICALITY	ignore	EXTENSION RL-ReconfigurationRequestFDD-RL-InformationList		PRESENCE 	optional}|
	{ ID id-DL-ReferencePowerInformation					CRITICALITY ignore	EXTENSION DL-ReferencePowerInformation				PRESENCE optional	}|
	{ ID id-HSDSCH-FDD-Information					CRITICALITY reject	EXTENSION HSDSCH-FDD-Information			PRESENCE optional}|
	{ ID id-HSDSCH-Information-to-Modify-Unsynchronised	CRITICALITY reject		EXTENSION HSDSCH-Information-to-Modify-Unsynchronised	PRESENCE optional}|
	{ ID id-HSDSCH-MACdFlows-to-Add					CRITICALITY reject		EXTENSION HSDSCH-MACdFlows-Information			PRESENCE optional}|
	{ ID id-HSDSCH-MACdFlows-to-Delete				CRITICALITY reject		EXTENSION HSDSCH-MACdFlows-to-Delete			PRESENCE optional}|
	{ ID id-HSPDSCH-RL-ID							CRITICALITY reject		EXTENSION RL-ID											PRESENCE optional}|
	{ ID id-EDPCH-Information-RLReconfRequest-FDD	CRITICALITY	reject		EXTENSION EDPCH-Information-RLReconfRequest-FDD		PRESENCE optional}|
	{ ID id-EDCH-FDD-Information					CRITICALITY	reject		EXTENSION EDCH-FDD-Information						PRESENCE optional}|
	{ ID id-EDCH-FDD-Information-To-Modify			CRITICALITY	reject		EXTENSION EDCH-FDD-Information-To-Modify		PRESENCE optional}|
	{ ID id-EDCH-MACdFlows-To-Add					CRITICALITY reject		EXTENSION EDCH-MACdFlows-Information				PRESENCE optional}|
	{ ID id-EDCH-MACdFlows-To-Delete				CRITICALITY	reject		EXTENSION EDCH-MACdFlows-To-Delete				PRESENCE optional}|
	{ ID id-Serving-EDCHRL-Id						CRITICALITY	reject		EXTENSION EDCH-Serving-RL							PRESENCE optional}|
	{ ID id-CPC-Information							CRITICALITY	reject		EXTENSION CPC-Information							PRESENCE optional}|
	{ ID id-NoOfTargetCellHS-SCCH-Order				CRITICALITY	ignore		EXTENSION NoOfTargetCellHS-SCCH-Order			PRESENCE optional}|
	{ ID id-Additional-HS-Cell-Information-RL-Reconf-Req	CRITICALITY	reject		EXTENSION Additional-HS-Cell-Information-RL-Reconf-Req				PRESENCE optional}|
	{ ID id-UE-AggregateMaximumBitRate				CRITICALITY ignore		EXTENSION UE-AggregateMaximumBitRate				PRESENCE optional	}|
	{ ID id-Additional-EDCH-Cell-Information-RL-Reconf-Req	CRITICALITY reject	EXTENSION Additional-EDCH-Cell-Information-RL-Reconf-Req		PRESENCE optional },
	...
}

Additional-HS-Cell-Information-RL-Reconf-Req	::= SEQUENCE (SIZE (1..maxNrOfHSDSCH-1)) OF Additional-HS-Cell-Information-RL-Reconf-Req-ItemIEs

Additional-HS-Cell-Information-RL-Reconf-Req-ItemIEs	::=SEQUENCE{
	hSPDSCH-RL-ID									RL-ID,
	c-ID											C-ID										OPTIONAL,
	hS-DSCH-FDD-Secondary-Serving-Information		HS-DSCH-FDD-Secondary-Serving-Information	OPTIONAL,
	hS-DSCH-FDD-Secondary-Serving-Information-To-Modify-Unsynchronised		HS-DSCH-FDD-Secondary-Serving-Information-To-Modify-Unsynchronised	OPTIONAL,
	hS-DSCH-Secondary-Serving-Remove				HS-DSCH-Secondary-Serving-Remove	OPTIONAL,
	iE-Extensions					ProtocolExtensionContainer { { Additional-HS-Cell-Information-RL-Reconf-Req-ExtIEs} } OPTIONAL,
	...
}

Additional-HS-Cell-Information-RL-Reconf-Req-ExtIEs	RNSAP-PROTOCOL-EXTENSION ::= {
	...
}

Additional-EDCH-Cell-Information-RL-Reconf-Req	::=SEQUENCE{
	setup-Or-ConfigurationChange-Or-Removal-Of-EDCH-On-secondary-UL-Frequency		Setup-Or-ConfigurationChange-Or-Removal-Of-EDCH-On-secondary-UL-Frequency,
	iE-Extensions					ProtocolExtensionContainer { { Additional-EDCH-Cell-Information-RL-Reconf-Req-ExtIEs} } OPTIONAL,
	...
}

Additional-EDCH-Cell-Information-RL-Reconf-Req-ExtIEs	RNSAP-PROTOCOL-EXTENSION ::= {
	...
}

RL-ReconfigurationRequestFDD-RL-InformationList ::= SEQUENCE (SIZE (0..maxNrOfRLs)) OF ProtocolIE-Single-Container {
	{RL-ReconfigurationRequestFDD-RL-Information-ListItem} }

RL-ReconfigurationRequestFDD-RL-Information-ListItem RNSAP-PROTOCOL-IES ::= {
	{ ID id-RL-ReconfigurationRequestFDD-RL-Information-IEs	CRITICALITY ignore	TYPE RL-ReconfigurationRequestFDD-RL-Information-IEs	PRESENCE optional	}
}

RL-ReconfigurationRequestFDD-RL-Information-IEs ::= SEQUENCE {
	rL-ID					RL-ID,
	rL-Specific-DCH-Info	RL-Specific-DCH-Info OPTIONAL,
	iE-Extensions			ProtocolExtensionContainer { { RL-ReconfigurationRequestFDD-RL-Information-ExtIEs} } OPTIONAL,
	...
}

RL-ReconfigurationRequestFDD-RL-Information-ExtIEs RNSAP-PROTOCOL-EXTENSION ::= {
	{ ID id-RL-Specific-EDCH-Information		CRITICALITY reject	EXTENSION RL-Specific-EDCH-Information 		PRESENCE optional }|
	{ ID id-EDCH-RL-Indication					CRITICALITY reject	EXTENSION EDCH-RL-Indication						PRESENCE optional }|
	{ ID id-HSDSCH-PreconfigurationSetup		CRITICALITY ignore	EXTENSION HSDSCH-PreconfigurationSetup			PRESENCE optional }|
	{ ID id-Non-Serving-RL-Preconfig-Setup		CRITICALITY ignore	EXTENSION Non-Serving-RL-Preconfig-Setup		PRESENCE optional }|
	{ ID id-Non-Serving-RL-Preconfig-Removal	CRITICALITY ignore	EXTENSION Non-Serving-RL-Preconfig-Setup		PRESENCE optional },
	...
}

-- **************************************************************
--
-- RADIO LINK RECONFIGURATION REQUEST TDD
--
-- **************************************************************

RadioLinkReconfigurationRequestTDD ::= SEQUENCE {
	protocolIEs                     ProtocolIE-Container       {{RadioLinkReconfigurationRequestTDD-IEs}},
	protocolExtensions              ProtocolExtensionContainer {{RadioLinkReconfigurationRequestTDD-Extensions}}                   OPTIONAL,
	...
}

RadioLinkReconfigurationRequestTDD-IEs RNSAP-PROTOCOL-IES ::= {
	{ ID id-AllowedQueuingTime			CRITICALITY reject	TYPE AllowedQueuingTime				PRESENCE optional	} |
	{ ID id-UL-CCTrCH-InformationModifyList-RL-ReconfRqstTDD	CRITICALITY notify	TYPE UL-CCTrCH-InformationModifyList-RL-ReconfRqstTDD	PRESENCE optional	} |
	{ ID id-UL-CCTrCH-InformationDeleteList-RL-ReconfRqstTDD	CRITICALITY notify	TYPE UL-CCTrCH-InformationDeleteList-RL-ReconfRqstTDD	PRESENCE optional	} |
	{ ID id-DL-CCTrCH-InformationModifyList-RL-ReconfRqstTDD	CRITICALITY notify	TYPE DL-CCTrCH-InformationModifyList-RL-ReconfRqstTDD	PRESENCE optional	} |
	{ ID id-DL-CCTrCH-InformationDeleteList-RL-ReconfRqstTDD	CRITICALITY notify	TYPE DL-CCTrCH-InformationDeleteList-RL-ReconfRqstTDD	PRESENCE optional	} |
	{ ID id-TDD-DCHs-to-Modify		CRITICALITY reject	TYPE TDD-DCHs-to-Modify		PRESENCE optional	} |
	{ ID id-DCHs-to-Add-TDD		CRITICALITY reject	TYPE DCH-TDD-Information		PRESENCE optional	} |
	{ ID id-DCH-DeleteList-RL-ReconfRqstTDD		CRITICALITY reject	TYPE DCH-DeleteList-RL-ReconfRqstTDD		PRESENCE optional	},
	...
}

UL-CCTrCH-InformationModifyList-RL-ReconfRqstTDD		::= SEQUENCE (SIZE (0..maxNrOfCCTrCHs)) OF ProtocolIE-Single-Container { {UL-CCTrCH-InformationModifyList-RL-ReconfRqstTDD-IEs} }

UL-CCTrCH-InformationModifyList-RL-ReconfRqstTDD-IEs RNSAP-PROTOCOL-IES ::= {
	{ ID id-UL-CCTrCH-InformationModifyItem-RL-ReconfRqstTDD	CRITICALITY notify	TYPE UL-CCTrCH-InformationModifyItem-RL-ReconfRqstTDD	PRESENCE mandatory	}
}

UL-CCTrCH-InformationModifyItem-RL-ReconfRqstTDD ::= SEQUENCE {
	cCTrCH-ID					CCTrCH-ID,
	tFCS						TFCS		OPTIONAL,
	iE-Extensions					ProtocolExtensionContainer { {UL-CCTrCH-InformationModifyItem-RL-ReconfRqstTDD-ExtIEs} } OPTIONAL,
	...
}

UL-CCTrCH-InformationModifyItem-RL-ReconfRqstTDD-ExtIEs RNSAP-PROTOCOL-EXTENSION ::= {
{ ID id-UL-SIRTarget      CRITICALITY reject      EXTENSION       UL-SIR      PRESENCE	optional   },
    -- Applicable to 1.28Mcps TDD only
	...
}

UL-CCTrCH-InformationDeleteList-RL-ReconfRqstTDD		::= SEQUENCE (SIZE (0..maxNrOfCCTrCHs)) OF ProtocolIE-Single-Container { {UL-CCTrCH-InformationDeleteList-RL-ReconfRqstTDD-IEs} }

UL-CCTrCH-InformationDeleteList-RL-ReconfRqstTDD-IEs RNSAP-PROTOCOL-IES ::= {
	{ ID id-UL-CCTrCH-InformationDeleteItem-RL-ReconfRqstTDD	CRITICALITY notify	TYPE UL-CCTrCH-InformationDeleteItem-RL-ReconfRqstTDD	PRESENCE mandatory	}
}

UL-CCTrCH-InformationDeleteItem-RL-ReconfRqstTDD ::= SEQUENCE {
	cCTrCH-ID					CCTrCH-ID,
	iE-Extensions					ProtocolExtensionContainer { {UL-CCTrCH-InformationDeleteItem-RL-ReconfRqstTDD-ExtIEs} } OPTIONAL,
	...
}

UL-CCTrCH-InformationDeleteItem-RL-ReconfRqstTDD-ExtIEs RNSAP-PROTOCOL-EXTENSION ::= {
	...
}

DL-CCTrCH-InformationModifyList-RL-ReconfRqstTDD		::= SEQUENCE (SIZE (0..maxNrOfCCTrCHs)) OF ProtocolIE-Single-Container { {DL-CCTrCH-InformationModifyList-RL-ReconfRqstTDD-IEs} }

DL-CCTrCH-InformationModifyList-RL-ReconfRqstTDD-IEs RNSAP-PROTOCOL-IES ::= {
	{ ID id-DL-CCTrCH-InformationModifyItem-RL-ReconfRqstTDD	CRITICALITY notify	TYPE DL-CCTrCH-InformationModifyItem-RL-ReconfRqstTDD	PRESENCE mandatory	}
}

DL-CCTrCH-InformationModifyItem-RL-ReconfRqstTDD ::= SEQUENCE {
	cCTrCH-ID					CCTrCH-ID,
	tFCS						TFCS		OPTIONAL,
	iE-Extensions					ProtocolExtensionContainer { {DL-CCTrCH-InformationModifyItem-RL-ReconfRqstTDD-ExtIEs} } OPTIONAL,
	...
}

DL-CCTrCH-InformationModifyItem-RL-ReconfRqstTDD-ExtIEs RNSAP-PROTOCOL-EXTENSION ::= {
	...
}

DL-CCTrCH-InformationDeleteList-RL-ReconfRqstTDD		::= SEQUENCE (SIZE (0..maxNrOfCCTrCHs)) OF ProtocolIE-Single-Container { {DL-CCTrCH-InformationDeleteList-RL-ReconfRqstTDD-IEs} }

DL-CCTrCH-InformationDeleteList-RL-ReconfRqstTDD-IEs RNSAP-PROTOCOL-IES ::= {
	{ ID id-DL-CCTrCH-InformationDeleteItem-RL-ReconfRqstTDD	CRITICALITY notify	TYPE DL-CCTrCH-InformationDeleteItem-RL-ReconfRqstTDD	PRESENCE mandatory	}
}

DL-CCTrCH-InformationDeleteItem-RL-ReconfRqstTDD ::= SEQUENCE {
	cCTrCH-ID					CCTrCH-ID,
	iE-Extensions					ProtocolExtensionContainer { {DL-CCTrCH-InformationDeleteItem-RL-ReconfRqstTDD-ExtIEs} } OPTIONAL,
	...
}

DL-CCTrCH-InformationDeleteItem-RL-ReconfRqstTDD-ExtIEs RNSAP-PROTOCOL-EXTENSION ::= {
	...
}

DCH-DeleteList-RL-ReconfRqstTDD				::= SEQUENCE (SIZE(0..maxNrOfDCHs)) OF DCH-DeleteItem-RL-ReconfRqstTDD

DCH-DeleteItem-RL-ReconfRqstTDD ::= SEQUENCE {
	dCH-ID						DCH-ID,
	iE-Extensions					ProtocolExtensionContainer { {DCH-DeleteItem-RL-ReconfRqstTDD-ExtIEs} } OPTIONAL,
	...
}

DCH-DeleteItem-RL-ReconfRqstTDD-ExtIEs RNSAP-PROTOCOL-EXTENSION ::= {
	...
}

RadioLinkReconfigurationRequestTDD-Extensions RNSAP-PROTOCOL-EXTENSION ::= {
{ ID id-RL-ReconfigurationRequestTDD-RL-Information	CRITICALITY	ignore	EXTENSION 	Multiple-RL-ReconfigurationRequestTDD-RL-Information		PRESENCE 	optional}|
	{ ID id-HSDSCH-TDD-Information				CRITICALITY reject		EXTENSION HSDSCH-TDD-Information		PRESENCE optional}|
	{ ID id-HSDSCH-Information-to-Modify-Unsynchronised	CRITICALITY reject		EXTENSION HSDSCH-Information-to-Modify-Unsynchronised	PRESENCE optional}|
	{ ID id-HSDSCH-MACdFlows-to-Add				CRITICALITY reject		EXTENSION HSDSCH-MACdFlows-Information		PRESENCE optional}|
	{ ID id-HSDSCH-MACdFlows-to-Delete			CRITICALITY reject		EXTENSION HSDSCH-MACdFlows-to-Delete		PRESENCE optional}|
	{ ID id-HSPDSCH-RL-ID						CRITICALITY reject		EXTENSION RL-ID											PRESENCE optional}|
	{ ID id-E-DCH-Information-Reconfig			CRITICALITY reject		EXTENSION E-DCH-Information-Reconfig		PRESENCE optional	}|
	{ ID id-E-DCH-Serving-RL-ID					CRITICALITY reject		EXTENSION RL-ID					PRESENCE optional	}|
	{ ID id-E-DCH-768-Information-Reconfig		CRITICALITY reject		EXTENSION E-DCH-768-Information-Reconfig		PRESENCE optional	}|
	{ ID id-E-DCH-LCR-Information-Reconfig		CRITICALITY reject		EXTENSION E-DCH-LCR-Information-Reconfig			PRESENCE optional	}|
	{ ID id-CPC-InformationLCR					CRITICALITY reject		EXTENSION CPC-InformationLCR							PRESENCE optional }|
	{ ID id-RNTI-Allocation-Indicator			CRITICALITY ignore		EXTENSION  RNTI-Allocation-Indicator				PRESENCE optional }|
	{ ID id-DCH-MeasurementType-Indicator		CRITICALITY reject		EXTENSION DCH-MeasurementType-Indicator		PRESENCE optional},
	...
}

Multiple-RL-ReconfigurationRequestTDD-RL-Information ::= SEQUENCE (SIZE (1..maxNrOfRLs)) OF RL-ReconfigurationRequestTDD-RL-Information

RL-ReconfigurationRequestTDD-RL-Information ::= SEQUENCE {
	rL-ID					RL-ID,
	rL-Specific-DCH-Info	RL-Specific-DCH-Info OPTIONAL,
	iE-Extensions			ProtocolExtensionContainer { { RL-ReconfigurationRequestTDD-RL-Information-ExtIEs} } OPTIONAL,
	...
}

RL-ReconfigurationRequestTDD-RL-Information-ExtIEs RNSAP-PROTOCOL-EXTENSION ::= {
	{ ID	id-UL-Synchronisation-Parameters-LCR			CRITICALITY	ignore		EXTENSION 	UL-Synchronisation-Parameters-LCR		PRESENCE 	optional	}|	-- Mandatory for 1.28Mcps TDD, Not Applicable to 3.84Mcps TDD or 7.68Mcps TDD
	{ ID id-NeedforIdleInterval							CRITICALITY ignore	EXTENSION	NeedforIdleInterval				PRESENCE optional },
	...
}

-- **************************************************************
--
-- RADIO LINK RECONFIGURATION RESPONSE FDD
--
-- **************************************************************

RadioLinkReconfigurationResponseFDD ::= SEQUENCE {
	protocolIEs                     ProtocolIE-Container       {{RadioLinkReconfigurationResponseFDD-IEs}},
	protocolExtensions              ProtocolExtensionContainer {{RadioLinkReconfigurationResponseFDD-Extensions}}                   OPTIONAL,
	...
}

RadioLinkReconfigurationResponseFDD-IEs RNSAP-PROTOCOL-IES ::= {
	{ ID id-RL-InformationResponseList-RL-ReconfRspFDD		CRITICALITY ignore	TYPE RL-InformationResponseList-RL-ReconfRspFDD			PRESENCE optional	} |
	{ ID id-CriticalityDiagnostics			CRITICALITY ignore	TYPE CriticalityDiagnostics			PRESENCE optional	},
	...
}

RL-InformationResponseList-RL-ReconfRspFDD		::= SEQUENCE (SIZE (0..maxNrOfRLs)) OF ProtocolIE-Single-Container { {RL-InformationResponse-RL-ReconfRspFDD-IEs} }

RL-InformationResponse-RL-ReconfRspFDD-IEs RNSAP-PROTOCOL-IES ::= {
	{ ID id-RL-InformationResponseItem-RL-ReconfRspFDD		CRITICALITY ignore	TYPE RL-InformationResponseItem-RL-ReconfRspFDD		PRESENCE mandatory	}
}

RL-InformationResponseItem-RL-ReconfRspFDD ::= SEQUENCE {
	rL-ID							RL-ID,
	max-UL-SIR						UL-SIR			OPTIONAL,
	min-UL-SIR						UL-SIR			OPTIONAL,
	maximumDLTxPower				DL-Power		OPTIONAL,
	minimumDLTxPower				DL-Power		OPTIONAL,
	not-Used-secondary-CCPCH-Info			NULL		OPTIONAL,
	dCHsInformationResponseList		DCH-InformationResponseList-RL-ReconfRspFDD	OPTIONAL,
	dL-CodeInformationList-RL-ReconfResp 	DL-CodeInformationList-RL-ReconfRspFDD	OPTIONAL,
	iE-Extensions					ProtocolExtensionContainer { {RL-InformationResponseItem-RL-ReconfRspFDD-ExtIEs} } OPTIONAL,
	...
}

RL-InformationResponseItem-RL-ReconfRspFDD-ExtIEs RNSAP-PROTOCOL-EXTENSION ::= {
	{ ID id-DL-PowerBalancing-UpdatedIndicator		CRITICALITY ignore	EXTENSION DL-PowerBalancing-UpdatedIndicator			PRESENCE optional }|
	{ ID id-EDCH-FDD-InformationResponse			CRITICALITY ignore	EXTENSION EDCH-FDD-InformationResponse					PRESENCE optional }|
	{ ID id-EDCH-RLSet-Id							CRITICALITY ignore	EXTENSION RL-Set-ID												PRESENCE optional }|
	{ ID id-EDCH-FDD-DL-ControlChannelInformation	CRITICALITY ignore	EXTENSION EDCH-FDD-DL-ControlChannelInformation		PRESENCE optional }|
	{ ID id-F-DPCH-SlotFormat						CRITICALITY ignore	EXTENSION F-DPCH-SlotFormat									PRESENCE optional }|
	{ ID id-HSDSCH-PreconfigurationInfo				CRITICALITY ignore	EXTENSION HSDSCH-PreconfigurationInfo						PRESENCE optional }|
	{ ID id-Non-Serving-RL-Preconfig-Info			CRITICALITY ignore	EXTENSION Non-Serving-RL-Preconfig-Info					PRESENCE optional },
	...
}

DCH-InformationResponseList-RL-ReconfRspFDD				::= ProtocolIE-Single-Container { {DCH-InformationResponseListIEs-RL-ReconfRspFDD} }

DCH-InformationResponseListIEs-RL-ReconfRspFDD RNSAP-PROTOCOL-IES ::= {
	{ ID id-DCH-InformationResponse		CRITICALITY ignore	TYPE DCH-InformationResponse		PRESENCE mandatory	}
}

DL-CodeInformationList-RL-ReconfRspFDD ::= ProtocolIE-Single-Container {{ DL-CodeInformationListIEs-RL-ReconfRspFDD }}

DL-CodeInformationListIEs-RL-ReconfRspFDD RNSAP-PROTOCOL-IES ::= {
	{ ID id-FDD-DL-CodeInformation   CRITICALITY ignore	TYPE FDD-DL-CodeInformation		PRESENCE optional }
}

RadioLinkReconfigurationResponseFDD-Extensions RNSAP-PROTOCOL-EXTENSION ::= {
	{ ID id-HSDSCH-RNTI							CRITICALITY ignore		EXTENSION HSDSCH-RNTI									PRESENCE optional }|
	{ ID id-HSDSCH-FDD-Information-Response		CRITICALITY ignore		EXTENSION HSDSCH-FDD-Information-Response		PRESENCE optional }|
	{ ID id-MAChs-ResetIndicator				CRITICALITY ignore		EXTENSION MAChs-ResetIndicator						PRESENCE optional }|
	{ ID id-Continuous-Packet-Connectivity-HS-SCCH-Less-Information-Response				CRITICALITY ignore		EXTENSION Continuous-Packet-Connectivity-HS-SCCH-Less-Information-Response						PRESENCE optional }|
	{ ID id-Additional-HS-Cell-Information-Response	CRITICALITY ignore		EXTENSION Additional-HS-Cell-Information-Response-List		PRESENCE optional }|
	{ ID id-Additional-EDCH-Cell-Information-ResponseRLReconf		CRITICALITY ignore	EXTENSION	Additional-EDCH-Cell-Information-Response-RLReconf-List			PRESENCE optional },
	...
}

-- **************************************************************
--
-- RADIO LINK RECONFIGURATION RESPONSE TDD
--
-- **************************************************************

RadioLinkReconfigurationResponseTDD ::= SEQUENCE {
	protocolIEs                     ProtocolIE-Container       {{RadioLinkReconfigurationResponseTDD-IEs}},
	protocolExtensions              ProtocolExtensionContainer {{RadioLinkReconfigurationResponseTDD-Extensions}}                   OPTIONAL,
	...
}

RadioLinkReconfigurationResponseTDD-IEs RNSAP-PROTOCOL-IES ::= {
	{ ID id-RL-InformationResponse-RL-ReconfRspTDD		CRITICALITY ignore	TYPE RL-InformationResponse-RL-ReconfRspTDD			PRESENCE optional	} |
	--This RL-InformationResponse-RL-ReconfRspTDD is for the first RL repetition in the list.
	--Repetitions 2 and on are defined in Multiple-RL-InformationResponse-RL-ReconfRspTDD.
	{ ID id-CriticalityDiagnostics			CRITICALITY ignore	TYPE CriticalityDiagnostics			PRESENCE optional	},
	...
}

RL-InformationResponse-RL-ReconfRspTDD ::= SEQUENCE {
	rL-ID							RL-ID,
	max-UL-SIR						UL-SIR			OPTIONAL,
	min-UL-SIR						UL-SIR			OPTIONAL,
	maximumDLTxPower				DL-Power		OPTIONAL,
	minimumDLTxPower				DL-Power		OPTIONAL,
	dCHsInformationResponseList		DCH-InformationResponseList-RL-ReconfRspTDD	OPTIONAL,
	iE-Extensions					ProtocolExtensionContainer { {RL-InformationResponse-RL-ReconfRspTDD-ExtIEs} } OPTIONAL,
	...
}

RL-InformationResponse-RL-ReconfRspTDD-ExtIEs RNSAP-PROTOCOL-EXTENSION ::= {
	{ ID id-DL-CCTrCH-InformationList-RL-ReconfRspTDD	CRITICALITY ignore	EXTENSION DL-CCTrCH-InformationList-RL-ReconfRspTDD		PRESENCE optional }|
	{ ID id-UL-TimingAdvanceCtrl-LCR					CRITICALITY ignore	EXTENSION UL-TimingAdvanceCtrl-LCR		PRESENCE optional },
	--For 1.28Mcps TDD only
	...
}

DL-CCTrCH-InformationList-RL-ReconfRspTDD ::= SEQUENCE (SIZE (1..maxNrOfCCTrCHs)) OF DL-CCTrCH-InformationItem-RL-ReconfRspTDD

DL-CCTrCH-InformationItem-RL-ReconfRspTDD ::= SEQUENCE {
	cCTrCH-ID									CCTrCH-ID,
	dl-DPCH-ModifyInformation-LCR				DL-DPCH-InformationModifyList-LCR-RL-ReconfRspTDD			OPTIONAL,
	--For 1.28Mcps TDD only
	cCTrCH-Maximum-DL-Power						DL-Power				OPTIONAL,
	--For 3.84Mcps TDD and 7.68Mcps TDD only, this is a DCH type CCTrCH power
	cCTrCH-Minimum-DL-Power						DL-Power				OPTIONAL,
	--For 3.84Mcps TDD and 7.68Mcps TDD only, this is a DCH type CCTrCH power
	iE-Extensions								ProtocolExtensionContainer { { DL-CCTrCH-InformationItem-RL-ReconfRspTDD-ExtIEs} }		OPTIONAL,
	...
}

DL-CCTrCH-InformationItem-RL-ReconfRspTDD-ExtIEs   RNSAP-PROTOCOL-EXTENSION ::= {
	...
}

DL-DPCH-InformationModifyList-LCR-RL-ReconfRspTDD  ::= ProtocolIE-Single-Container {{ DL-DPCH-InformationModifyListIEs-LCR-RL-ReconfRspTDD }}

DL-DPCH-InformationModifyListIEs-LCR-RL-ReconfRspTDD RNSAP-PROTOCOL-IES ::= {
	{ID id-DL-DPCH-InformationModifyItem-LCR-RL-ReconfRspTDD   CRITICALITY ignore	TYPE  DL-DPCH-InformationModifyItem-LCR-RL-ReconfRspTDD		PRESENCE optional },
	...
}

DL-DPCH-InformationModifyItem-LCR-RL-ReconfRspTDD  ::= SEQUENCE {
	dL-Timeslot-LCR-InformationModifyList-RL-ReconfRqstTDD		DL-Timeslot-LCR-InformationModifyList-RL-ReconfRspTDD			OPTIONAL,
	iE-Extensions	ProtocolExtensionContainer { { DL-DPCH-InformationModifyItem-LCR-RL-ReconfRspTDD-ExtIEs} }		OPTIONAL,
	...
}

DL-DPCH-InformationModifyItem-LCR-RL-ReconfRspTDD-ExtIEs  RNSAP-PROTOCOL-EXTENSION ::= {
	...
}

DL-Timeslot-LCR-InformationModifyList-RL-ReconfRspTDD ::= SEQUENCE (SIZE (1..maxNrOfDLTsLCR)) OF DL-Timeslot-LCR-InformationModifyItem-RL-ReconfRspTDD

DL-Timeslot-LCR-InformationModifyItem-RL-ReconfRspTDD	 ::= SEQUENCE {
	timeSlotLCR								TimeSlotLCR,
	maxPowerLCR								DL-Power	OPTIONAL,
	minPowerLCR								DL-Power	OPTIONAL,
	iE-Extensions							ProtocolExtensionContainer { { DL-Timeslot-LCR-InformationModifyItem-RL-ReconfRspTDD-ExtIEs} }		OPTIONAL,
	...
}

DL-Timeslot-LCR-InformationModifyItem-RL-ReconfRspTDD-ExtIEs RNSAP-PROTOCOL-EXTENSION ::= {
	...
}

DCH-InformationResponseList-RL-ReconfRspTDD				::= ProtocolIE-Single-Container { {DCH-InformationResponseListIEs-RL-ReconfRspTDD} }

DCH-InformationResponseListIEs-RL-ReconfRspTDD RNSAP-PROTOCOL-IES ::= {
	{ ID id-DCH-InformationResponse	CRITICALITY ignore	TYPE DCH-InformationResponse	PRESENCE optional	}
}

RadioLinkReconfigurationResponseTDD-Extensions RNSAP-PROTOCOL-EXTENSION ::= {
	{ ID id-HSDSCH-RNTI							CRITICALITY ignore		EXTENSION HSDSCH-RNTI									PRESENCE optional }|
	{ ID id-HSDSCH-TDD-Information-Response		CRITICALITY ignore		EXTENSION HSDSCH-TDD-Information-Response		PRESENCE optional }|
	{ ID id-MAChs-ResetIndicator				CRITICALITY ignore		EXTENSION MAChs-ResetIndicator						PRESENCE optional }|
	{ ID id-RL-ReconfigurationResponseTDD-RL-Information	CRITICALITY	ignore		EXTENSION 	Multiple-RL-InformationResponse-RL-ReconfRspTDD		PRESENCE 	optional}|
	{ ID id-E-DCH-Information-Response			CRITICALITY ignore		EXTENSION E-DCH-Information-Response		PRESENCE optional	}|
	{ ID id-E-DCH-768-Information-Response		CRITICALITY ignore		EXTENSION E-DCH-768-Information-Response		PRESENCE optional	}|
	{ ID id-E-DCH-LCR-Information-Response		CRITICALITY ignore		EXTENSION E-DCH-LCR-Information-Response		PRESENCE optional	}|
	{ ID id-PowerControlGAP						CRITICALITY ignore		EXTENSION ControlGAP				PRESENCE optional }|
	-- Applicable to 1.28Mcps TDD only
	{ ID id-IdleIntervalInformation				CRITICALITY ignore		EXTENSION	IdleIntervalInformation				PRESENCE optional }|
	{ ID id-ContinuousPacketConnectivity-DRX-Information-ResponseLCR	CRITICALITY ignore	EXTENSION ContinuousPacketConnectivity-DRX-Information-ResponseLCR			PRESENCE optional	}|
	{ ID id-HS-DSCH-Semi-PersistentScheduling-Information-ResponseLCR	CRITICALITY ignore	EXTENSION HS-DSCH-Semi-PersistentScheduling-Information-ResponseLCR			PRESENCE optional}|
	{ ID id-E-DCH-Semi-PersistentScheduling-Information-ResponseLCR		CRITICALITY ignore		EXTENSION E-DCH-Semi-PersistentScheduling-Information-ResponseLCR			PRESENCE optional}|
	{ ID id-E-RNTI-For-FACH						CRITICALITY ignore	EXTENSION E-RNTI											PRESENCE optional }|
	{ ID id-H-RNTI-For-FACH						CRITICALITY ignore	EXTENSION HSDSCH-RNTI										PRESENCE optional }|
	{ ID id-DCH-MeasurementOccasion-Information	CRITICALITY reject	EXTENSION DCH-MeasurementOccasion-Information		PRESENCE optional },
	...
}

Multiple-RL-InformationResponse-RL-ReconfRspTDD ::= SEQUENCE (SIZE (1..maxNrOfRLs-1)) OF RL-InformationResponse-RL-ReconfRspTDD
--Includes the 2nd through the max number of radio link information repetitions.

-- **************************************************************
--
-- RADIO LINK FAILURE INDICATION
--
-- **************************************************************

RadioLinkFailureIndication ::= SEQUENCE {
	protocolIEs                     ProtocolIE-Container       {{RadioLinkFailureIndication-IEs}},
	protocolExtensions              ProtocolExtensionContainer {{RadioLinkFailureIndication-Extensions}}                   OPTIONAL,
	...
}

RadioLinkFailureIndication-IEs RNSAP-PROTOCOL-IES ::= {
	{ ID id-Reporting-Object-RL-FailureInd	CRITICALITY ignore	TYPE Reporting-Object-RL-FailureInd		PRESENCE mandatory	},
	...
}

Reporting-Object-RL-FailureInd ::= CHOICE {
	rL						RL-RL-FailureInd,
	rL-Set					RL-Set-RL-FailureInd, --FDD only
	...,
	cCTrCH					CCTrCH-RL-FailureInd  --TDD only
}

RL-RL-FailureInd		 	::= SEQUENCE {
	rL-InformationList-RL-FailureInd		RL-InformationList-RL-FailureInd,
	iE-Extensions							ProtocolExtensionContainer { { RLItem-RL-FailureInd-ExtIEs} } OPTIONAL,
	...
}

RLItem-RL-FailureInd-ExtIEs RNSAP-PROTOCOL-EXTENSION ::= {
	...
}

RL-InformationList-RL-FailureInd		 	::= SEQUENCE (SIZE (1..maxNrOfRLs)) OF ProtocolIE-Single-Container { {RL-Information-RL-FailureInd-IEs} }

RL-Information-RL-FailureInd-IEs RNSAP-PROTOCOL-IES ::= {
	{ ID id-RL-Information-RL-FailureInd		CRITICALITY ignore	TYPE RL-Information-RL-FailureInd		PRESENCE mandatory	}
}

RL-Information-RL-FailureInd ::= SEQUENCE {
	rL-ID						RL-ID,
	cause						Cause,
	iE-Extensions					ProtocolExtensionContainer { {RL-Information-RL-FailureInd-ExtIEs} } OPTIONAL,
	...
}

RL-Information-RL-FailureInd-ExtIEs RNSAP-PROTOCOL-EXTENSION ::= {
	...
}

RL-Set-RL-FailureInd		 	::= SEQUENCE {
	rL-Set-InformationList-RL-FailureInd	RL-Set-InformationList-RL-FailureInd,
	iE-Extensions							ProtocolExtensionContainer { { RL-SetItem-RL-FailureInd-ExtIEs} } OPTIONAL,
	...
}

RL-SetItem-RL-FailureInd-ExtIEs RNSAP-PROTOCOL-EXTENSION ::= {
	...
}

RL-Set-InformationList-RL-FailureInd		 	::= SEQUENCE (SIZE (1..maxNrOfRLSets)) OF ProtocolIE-Single-Container { {RL-Set-Information-RL-FailureInd-IEs} }

RL-Set-Information-RL-FailureInd-IEs RNSAP-PROTOCOL-IES ::= {
	{ ID id-RL-Set-Information-RL-FailureInd		CRITICALITY ignore	TYPE RL-Set-Information-RL-FailureInd		PRESENCE mandatory	}
}

RL-Set-Information-RL-FailureInd ::= SEQUENCE {
	rL-Set-ID						RL-Set-ID,
	cause							Cause,
	iE-Extensions					ProtocolExtensionContainer { {RL-Set-Information-RL-FailureInd-ExtIEs} } OPTIONAL,
	...
}

RL-Set-Information-RL-FailureInd-ExtIEs RNSAP-PROTOCOL-EXTENSION ::= {
	...
}

RadioLinkFailureIndication-Extensions RNSAP-PROTOCOL-EXTENSION ::= {
	...
}

CCTrCH-RL-FailureInd ::= SEQUENCE {
	rL-ID										RL-ID,
	cCTrCH-InformationList-RL-FailureInd		CCTrCH-InformationList-RL-FailureInd,
	iE-Extensions							ProtocolExtensionContainer { { CCTrCHItem-RL-FailureInd-ExtIEs } }		OPTIONAL,
	...
 }

CCTrCHItem-RL-FailureInd-ExtIEs RNSAP-PROTOCOL-EXTENSION ::= {
	...
}

CCTrCH-InformationList-RL-FailureInd ::= SEQUENCE (SIZE (1..maxNrOfCCTrCHs)) OF ProtocolIE-Single-Container {{ CCTrCH-InformationItemIE-RL-FailureInd}}

CCTrCH-InformationItemIE-RL-FailureInd RNSAP-PROTOCOL-IES ::= {
 	{ ID	id-CCTrCH-InformationItem-RL-FailureInd			CRITICALITY		ignore			TYPE	CCTrCH-InformationItem-RL-FailureInd			PRESENCE	mandatory}
 }

CCTrCH-InformationItem-RL-FailureInd ::= SEQUENCE {
 	cCTrCH-ID									CCTrCH-ID,
	cause										Cause,
	iE-Extensions								ProtocolExtensionContainer { { CCTrCH-InformationItem-RL-FailureInd-ExtIEs } }		OPTIONAL,
	...
 }

CCTrCH-InformationItem-RL-FailureInd-ExtIEs RNSAP-PROTOCOL-EXTENSION ::= {
	...
}

-- **************************************************************
--
-- RADIO LINK PREEMPTION REQUIRED INDICATION
--
-- **************************************************************

RadioLinkPreemptionRequiredIndication ::= SEQUENCE {
	protocolIEs                     ProtocolIE-Container       {{RadioLinkPreemptionRequiredIndication-IEs}},
	protocolExtensions              ProtocolExtensionContainer {{RadioLinkPreemptionRequiredIndication-Extensions}}                   OPTIONAL,
	...
}

RadioLinkPreemptionRequiredIndication-IEs RNSAP-PROTOCOL-IES ::= {
	{ ID id-RL-InformationList-RL-PreemptRequiredInd	CRITICALITY ignore	TYPE RL-InformationList-RL-PreemptRequiredInd		PRESENCE optional	},
	...
}

RL-InformationList-RL-PreemptRequiredInd			::= SEQUENCE (SIZE (1..maxNrOfRLs)) OF ProtocolIE-Single-Container { {RL-InformationItemIEs-RL-PreemptRequiredInd} }

RL-InformationItemIEs-RL-PreemptRequiredInd RNSAP-PROTOCOL-IES ::= {
	{ ID id-RL-InformationItem-RL-PreemptRequiredInd		CRITICALITY ignore	TYPE RL-InformationItem-RL-PreemptRequiredInd		PRESENCE mandatory	}
}

RL-InformationItem-RL-PreemptRequiredInd::= SEQUENCE {
	rL-ID						RL-ID,
	iE-Extensions				ProtocolExtensionContainer { {RL-Information-RL-PreemptRequiredInd-ExtIEs} } OPTIONAL,
	...
}

RL-Information-RL-PreemptRequiredInd-ExtIEs RNSAP-PROTOCOL-EXTENSION ::= {
	{ ID id-EDCH-MacdFlowSpecificInformationList-RL-PreemptRequiredInd  CRITICALITY ignore	EXTENSION EDCH-MacdFlowSpecificInformationList-RL-PreemptRequiredInd PRESENCE optional },
	...
}

RadioLinkPreemptionRequiredIndication-Extensions RNSAP-PROTOCOL-EXTENSION ::= {
	{ ID id-HSDSCHMacdFlowSpecificInformationList-RL-PreemptRequiredInd  CRITICALITY ignore	EXTENSION HSDSCHMacdFlowSpecificInformationList-RL-PreemptRequiredInd PRESENCE optional },
	...
}

HSDSCHMacdFlowSpecificInformationList-RL-PreemptRequiredInd	::= SEQUENCE (SIZE (1.. maxNrOfMACdFlows)) OF ProtocolIE-Single-Container { {HSDSCHMacdFlowSpecificInformationItemIEs-RL-PreemptRequiredInd} }

HSDSCHMacdFlowSpecificInformationItemIEs-RL-PreemptRequiredInd RNSAP-PROTOCOL-IES ::= {
	{ ID id-HSDSCHMacdFlowSpecificInformationItem-RL-PreemptRequiredInd		CRITICALITY ignore	TYPE HSDSCHMacdFlowSpecificInformationItem-RL-PreemptRequiredInd	PRESENCE mandatory	}
}

HSDSCHMacdFlowSpecificInformationItem-RL-PreemptRequiredInd ::= SEQUENCE {
	hSDSCH-MACdFlow-ID						HSDSCH-MACdFlow-ID,
	iE-Extensions				ProtocolExtensionContainer { { HSDSCHMacdFlowSpecificInformation-RL-PreemptRequiredInd-ExtIEs} } OPTIONAL,
	...
}

HSDSCHMacdFlowSpecificInformation-RL-PreemptRequiredInd-ExtIEs RNSAP-PROTOCOL-EXTENSION ::= {
	...
}

EDCH-MacdFlowSpecificInformationList-RL-PreemptRequiredInd	::= SEQUENCE (SIZE (1.. maxNrOfEDCHMACdFlows)) OF ProtocolIE-Single-Container { {EDCH-MacdFlowSpecificInformationItemIEs-RL-PreemptRequiredInd} }

EDCH-MacdFlowSpecificInformationItemIEs-RL-PreemptRequiredInd RNSAP-PROTOCOL-IES ::= {
	{ ID id-EDCH-MacdFlowSpecificInformationItem-RL-PreemptRequiredInd		CRITICALITY ignore	TYPE EDCH-MacdFlowSpecificInformationItem-RL-PreemptRequiredInd	PRESENCE mandatory	}
}

EDCH-MacdFlowSpecificInformationItem-RL-PreemptRequiredInd ::= SEQUENCE {
	eDCH-MACdFlow-ID			EDCH-MACdFlow-ID,
	iE-Extensions				ProtocolExtensionContainer { { EDCH-MacdFlowSpecificInformation-RL-PreemptRequiredInd-ExtIEs} } OPTIONAL,
	...
}

EDCH-MacdFlowSpecificInformation-RL-PreemptRequiredInd-ExtIEs RNSAP-PROTOCOL-EXTENSION ::= {
	...
}


-- **************************************************************
--
-- RADIO LINK RESTORE INDICATION
--
-- **************************************************************

RadioLinkRestoreIndication ::= SEQUENCE {
	protocolIEs                     ProtocolIE-Container       {{RadioLinkRestoreIndication-IEs}},
	protocolExtensions              ProtocolExtensionContainer {{RadioLinkRestoreIndication-Extensions}}                   OPTIONAL,
	...
}

RadioLinkRestoreIndication-IEs RNSAP-PROTOCOL-IES ::= {
	{ ID id-Reporing-Object-RL-RestoreInd	CRITICALITY ignore	TYPE Reporting-Object-RL-RestoreInd		PRESENCE mandatory	},
	...
}

Reporting-Object-RL-RestoreInd ::= CHOICE {
	rL						RL-RL-RestoreInd, --TDD only
	rL-Set					RL-Set-RL-RestoreInd, --FDD only
	...,
	cCTrCH					CCTrCH-RL-RestoreInd  --TDD only
}

RL-RL-RestoreInd ::= SEQUENCE {
	rL-InformationList-RL-RestoreInd		RL-InformationList-RL-RestoreInd,
	iE-Extensions							ProtocolExtensionContainer { { RLItem-RL-RestoreInd-ExtIEs} } OPTIONAL,
	...
}

RLItem-RL-RestoreInd-ExtIEs RNSAP-PROTOCOL-EXTENSION ::= {
	...
}

RL-InformationList-RL-RestoreInd		 	::= SEQUENCE (SIZE (1..maxNrOfRLs)) OF ProtocolIE-Single-Container { {RL-Information-RL-RestoreInd-IEs} }

RL-Information-RL-RestoreInd-IEs RNSAP-PROTOCOL-IES ::= {
	{ ID id-RL-Information-RL-RestoreInd		CRITICALITY ignore	TYPE RL-Information-RL-RestoreInd		PRESENCE mandatory	}
}

RL-Information-RL-RestoreInd ::= SEQUENCE {
	rL-ID						RL-ID,
	iE-Extensions					ProtocolExtensionContainer { {RL-Information-RL-RestoreInd-ExtIEs} } OPTIONAL,
	...
}

RL-Information-RL-RestoreInd-ExtIEs RNSAP-PROTOCOL-EXTENSION ::= {
	...
}

RL-Set-RL-RestoreInd ::= SEQUENCE {
	rL-Set-InformationList-RL-RestoreInd	RL-Set-InformationList-RL-RestoreInd,
	iE-Extensions							ProtocolExtensionContainer { { RL-SetItem-RL-RestoreInd-ExtIEs} } OPTIONAL,
	...
}

RL-SetItem-RL-RestoreInd-ExtIEs RNSAP-PROTOCOL-EXTENSION ::= {
	...
}

RL-Set-InformationList-RL-RestoreInd		 	::= SEQUENCE (SIZE (1..maxNrOfRLSets)) OF ProtocolIE-Single-Container { {RL-Set-Information-RL-RestoreInd-IEs} }

RL-Set-Information-RL-RestoreInd-IEs RNSAP-PROTOCOL-IES ::= {
	{ ID id-RL-Set-Information-RL-RestoreInd		CRITICALITY ignore	TYPE RL-Set-Information-RL-RestoreInd		PRESENCE mandatory	}
}

RL-Set-Information-RL-RestoreInd ::= SEQUENCE {
	rL-Set-ID						RL-Set-ID,
	iE-Extensions					ProtocolExtensionContainer { {RL-Set-Information-RL-RestoreInd-ExtIEs} } OPTIONAL,
	...
}

RL-Set-Information-RL-RestoreInd-ExtIEs RNSAP-PROTOCOL-EXTENSION ::= {
	...
}

RadioLinkRestoreIndication-Extensions RNSAP-PROTOCOL-EXTENSION ::= {
	...
}

CCTrCH-RL-RestoreInd ::= SEQUENCE {
	rL-ID										RL-ID,
	cCTrCH-InformationList-RL-RestoreInd		CCTrCH-InformationList-RL-RestoreInd,
	iE-Extensions							ProtocolExtensionContainer { { CCTrCHItem-RL-RestoreInd-ExtIEs } }		OPTIONAL,
	...
 }

CCTrCHItem-RL-RestoreInd-ExtIEs RNSAP-PROTOCOL-EXTENSION ::= {
	...
}

CCTrCH-InformationList-RL-RestoreInd ::= SEQUENCE (SIZE (1..maxNrOfCCTrCHs)) OF ProtocolIE-Single-Container {{ CCTrCH-InformationItemIE-RL-RestoreInd}}

CCTrCH-InformationItemIE-RL-RestoreInd RNSAP-PROTOCOL-IES ::= {
 	{ ID	id-CCTrCH-InformationItem-RL-RestoreInd			CRITICALITY		ignore			TYPE	CCTrCH-InformationItem-RL-RestoreInd			PRESENCE	mandatory}
 }

CCTrCH-InformationItem-RL-RestoreInd ::= SEQUENCE {
 	cCTrCH-ID										CCTrCH-ID,
	iE-Extensions								ProtocolExtensionContainer { { CCTrCH-InformationItem-RL-RestoreInd-ExtIEs } }		OPTIONAL,
	...
 }

CCTrCH-InformationItem-RL-RestoreInd-ExtIEs RNSAP-PROTOCOL-EXTENSION ::= {
	...
}

-- **************************************************************
--
-- DOWNLINK POWER CONTROL REQUEST
--
-- **************************************************************

DL-PowerControlRequest ::= SEQUENCE {
	protocolIEs                     ProtocolIE-Container       {{DL-PowerControlRequest-IEs}},
	protocolExtensions              ProtocolExtensionContainer {{DL-PowerControlRequest-Extensions}}                   OPTIONAL,
	...
}

DL-PowerControlRequest-IEs RNSAP-PROTOCOL-IES ::= {
	{ ID id-PowerAdjustmentType	CRITICALITY ignore	TYPE PowerAdjustmentType	PRESENCE mandatory} |
	{ ID id-DLReferencePower	CRITICALITY ignore	TYPE DL-Power	PRESENCE conditional} |
	-- This IE shall be present if Power Adjustment Type IE equals to 'Common'
	{ ID id-InnerLoopDLPCStatus	CRITICALITY ignore	TYPE InnerLoopDLPCStatus	PRESENCE optional } |
	{ ID id-DLReferencePowerList-DL-PC-Rqst	CRITICALITY ignore	TYPE DL-ReferencePowerInformationList-DL-PC-Rqst	PRESENCE conditional} |
	-- This IE shall be present if Power Adjustment Type IE equals to 'Individual'
	{ ID id-MaxAdjustmentStep	CRITICALITY ignore	TYPE MaxAdjustmentStep	PRESENCE conditional } |
	-- This IE shall be present if Power Adjustment Type IE equals to 'Common' or 'Individual'
	{ ID id-AdjustmentPeriod	CRITICALITY ignore	TYPE AdjustmentPeriod	PRESENCE conditional }|
	-- This IE shall be present if Power Adjustment Type IE equals to 'Common' or 'Individual'
	{ ID id-AdjustmentRatio	CRITICALITY ignore	TYPE ScaledAdjustmentRatio	PRESENCE conditional },
	-- This IE shall be present if Power Adjustment Type IE equals to 'Common' or 'Individual'
	...
}

DL-ReferencePowerInformationList-DL-PC-Rqst 		::= SEQUENCE (SIZE (1..maxNrOfRLs)) OF ProtocolIE-Single-Container { {DL-ReferencePowerInformation-DL-PC-Rqst-IEs} }

DL-ReferencePowerInformation-DL-PC-Rqst-IEs RNSAP-PROTOCOL-IES ::= {
	{ ID id-DL-ReferencePowerInformation-DL-PC-Rqst	CRITICALITY ignore	TYPE DL-ReferencePowerInformation-DL-PC-Rqst	PRESENCE mandatory	}
}

DL-ReferencePowerInformation-DL-PC-Rqst ::= SEQUENCE {
	rL-ID						RL-ID,
	dl-Reference-Power			DL-Power,
	iE-Extensions				ProtocolExtensionContainer { {DL-ReferencePowerInformation-DL-PC-Rqst-ExtIEs} } OPTIONAL,
	...
}

DL-ReferencePowerInformation-DL-PC-Rqst-ExtIEs RNSAP-PROTOCOL-EXTENSION ::= {
	...
}

DL-PowerControlRequest-Extensions RNSAP-PROTOCOL-EXTENSION ::= {
	...
}

-- **************************************************************
--
-- DOWNLINK POWER TIMESLOT CONTROL REQUEST TDD
--
-- **************************************************************

DL-PowerTimeslotControlRequest ::= SEQUENCE {
	protocolIEs                     ProtocolIE-Container       {{DL-PowerTimeslotControlRequest-IEs}},
	protocolExtensions              ProtocolExtensionContainer {{DL-PowerTimeslotControlRequest-Extensions}}                   OPTIONAL,
	...
}

DL-PowerTimeslotControlRequest-IEs RNSAP-PROTOCOL-IES ::= {
	{ ID id-timeSlot-ISCP	CRITICALITY ignore	TYPE DL-TimeSlot-ISCP-Info	PRESENCE optional},
	--Mandatory for 3.84Mcps TDD and 7.68 Mcps TDD only
	...
}

DL-PowerTimeslotControlRequest-Extensions RNSAP-PROTOCOL-EXTENSION ::= {
	{ ID id-timeSlot-ISCP-LCR-List-DL-PC-Rqst-TDD	CRITICALITY ignore		EXTENSION  DL-TimeSlot-ISCP-LCR-Information	PRESENCE optional}|
	--Mandatory for 1.28Mcps TDD only
	{ ID id-PrimCCPCH-RSCP-DL-PC-RqstTDD			CRITICALITY ignore		EXTENSION PrimaryCCPCH-RSCP							PRESENCE optional }|
	{ ID id-PrimaryCCPCH-RSCP-Delta					CRITICALITY ignore		EXTENSION PrimaryCCPCH-RSCP-Delta					PRESENCE optional },
	...
}

-- **************************************************************
--
-- PHYSICAL CHANNEL RECONFIGURATION REQUEST FDD
--
-- **************************************************************

PhysicalChannelReconfigurationRequestFDD ::= SEQUENCE {
	protocolIEs                     ProtocolIE-Container       {{PhysicalChannelReconfigurationRequestFDD-IEs}},
	protocolExtensions              ProtocolExtensionContainer {{PhysicalChannelReconfigurationRequestFDD-Extensions}}                   OPTIONAL,
	...
}

PhysicalChannelReconfigurationRequestFDD-IEs RNSAP-PROTOCOL-IES ::= {
	{ ID id-RL-Information-PhyChReconfRqstFDD	CRITICALITY reject	TYPE RL-Information-PhyChReconfRqstFDD		PRESENCE mandatory	},
	...
}

RL-Information-PhyChReconfRqstFDD ::= SEQUENCE {
	rL-ID						RL-ID,
	dl-CodeInformation				DL-CodeInformationList-PhyChReconfRqstFDD,
	iE-Extensions					ProtocolExtensionContainer { {RL-Information-PhyChReconfRqstFDD-ExtIEs} } OPTIONAL,
	...
}

RL-Information-PhyChReconfRqstFDD-ExtIEs RNSAP-PROTOCOL-EXTENSION ::= {
	{ ID id-F-DPCH-SlotFormat				CRITICALITY ignore	EXTENSION F-DPCH-SlotFormat		PRESENCE optional},
	...
}

DL-CodeInformationList-PhyChReconfRqstFDD 		::= ProtocolIE-Single-Container { {DL-CodeInformationListIEs-PhyChReconfRqstFDD} }

DL-CodeInformationListIEs-PhyChReconfRqstFDD RNSAP-PROTOCOL-IES ::= {
	{ ID id-FDD-DL-CodeInformation	CRITICALITY notify	TYPE FDD-DL-CodeInformation	PRESENCE mandatory	}
}

PhysicalChannelReconfigurationRequestFDD-Extensions RNSAP-PROTOCOL-EXTENSION ::= {
	...
}

-- **************************************************************
--
-- PHYSICAL CHANNEL RECONFIGURATION REQUEST TDD
--
-- **************************************************************

PhysicalChannelReconfigurationRequestTDD ::= SEQUENCE {
	protocolIEs                     ProtocolIE-Container       {{PhysicalChannelReconfigurationRequestTDD-IEs}},
	protocolExtensions              ProtocolExtensionContainer {{PhysicalChannelReconfigurationRequestTDD-Extensions}}                   OPTIONAL,
	...
}

PhysicalChannelReconfigurationRequestTDD-IEs RNSAP-PROTOCOL-IES ::= {
	{ ID id-RL-Information-PhyChReconfRqstTDD	CRITICALITY reject	TYPE RL-Information-PhyChReconfRqstTDD		PRESENCE mandatory	},
	...
}

RL-Information-PhyChReconfRqstTDD ::= SEQUENCE {
	rL-ID						RL-ID,
	ul-CCTrCH-Information		UL-CCTrCH-InformationList-PhyChReconfRqstTDD	OPTIONAL,
	dl-CCTrCH-Information		DL-CCTrCH-InformationList-PhyChReconfRqstTDD	OPTIONAL,
	iE-Extensions				ProtocolExtensionContainer { {RL-Information-PhyChReconfRqstTDD-ExtIEs} } OPTIONAL,
	...
}

RL-Information-PhyChReconfRqstTDD-ExtIEs RNSAP-PROTOCOL-EXTENSION ::= {
	{ ID id-HSPDSCH-Timeslot-InformationList-PhyChReconfRqstTDD			CRITICALITY reject	EXTENSION HSPDSCH-Timeslot-InformationList-PhyChReconfRqstTDD		PRESENCE optional } |
	--For 3.84Mcps TDD only
	{ ID id-HSPDSCH-Timeslot-InformationListLCR-PhyChReconfRqstTDD		CRITICALITY reject	EXTENSION HSPDSCH-Timeslot-InformationListLCR-PhyChReconfRqstTDD	PRESENCE optional }|
	--For 1.28Mcps TDD only
	{ ID id-HSPDSCH-Timeslot-InformationList-PhyChReconfRqstTDD768		CRITICALITY reject	EXTENSION HSPDSCH-Timeslot-InformationList-PhyChReconfRqstTDD768		PRESENCE optional }|
	--For 7.68Mcps TDD only
	{ ID id-UARFCNforNt													CRITICALITY ignore	EXTENSION UARFCN		PRESENCE optional },
	-- Applicable to 1.28Mcps TDD only
	...
}

UL-CCTrCH-InformationList-PhyChReconfRqstTDD 		::= ProtocolIE-Single-Container { {UL-CCTrCH-InformationListIEs-PhyChReconfRqstTDD} }

UL-CCTrCH-InformationListIEs-PhyChReconfRqstTDD RNSAP-PROTOCOL-IES ::= {
	{ ID id-UL-CCTrCH-InformationListIE-PhyChReconfRqstTDD		CRITICALITY reject	TYPE UL-CCTrCH-InformationListIE-PhyChReconfRqstTDD		PRESENCE mandatory	}
}

UL-CCTrCH-InformationListIE-PhyChReconfRqstTDD ::= SEQUENCE (SIZE (1..maxNrOfCCTrCHs)) OF UL-CCTrCH-InformationItem-PhyChReconfRqstTDD

UL-CCTrCH-InformationItem-PhyChReconfRqstTDD ::= SEQUENCE {
	cCTrCH-ID						CCTrCH-ID,
	ul-DPCH-Information				UL-DPCH-InformationList-PhyChReconfRqstTDD,
	iE-Extensions					ProtocolExtensionContainer { {UL-CCTrCH-InformationItem-PhyChReconfRqstTDD-ExtIEs} } OPTIONAL,
	...
}

UL-CCTrCH-InformationItem-PhyChReconfRqstTDD-ExtIEs RNSAP-PROTOCOL-EXTENSION ::= {
	...
}

UL-DPCH-InformationList-PhyChReconfRqstTDD ::= ProtocolIE-Single-Container {{UL-DPCH-InformationListIEs-PhyChReconfRqstTDD}}

UL-DPCH-InformationListIEs-PhyChReconfRqstTDD RNSAP-PROTOCOL-IES ::= {
	{ ID id-UL-DPCH-InformationItem-PhyChReconfRqstTDD   CRITICALITY notify	TYPE UL-DPCH-InformationItem-PhyChReconfRqstTDD		PRESENCE mandatory }
}

UL-DPCH-InformationItem-PhyChReconfRqstTDD ::= SEQUENCE {
	repetitionPeriod				RepetitionPeriod		OPTIONAL,
	repetitionLength				RepetitionLength		OPTIONAL,
	tDD-DPCHOffset					TDD-DPCHOffset			OPTIONAL,
	uL-Timeslot-InformationList-PhyChReconfRqstTDD			UL-Timeslot-InformationList-PhyChReconfRqstTDD		OPTIONAL,
	--For 3.84Mcps TDD only
	iE-Extensions					ProtocolExtensionContainer { {UL-DPCH-InformationItem-PhyChReconfRqstTDD-ExtIEs} } OPTIONAL,
	...
}

UL-DPCH-InformationItem-PhyChReconfRqstTDD-ExtIEs RNSAP-PROTOCOL-EXTENSION ::= {
	{ ID id-UL-Timeslot-LCR-InformationList-PhyChReconfRqstTDD   CRITICALITY reject		EXTENSION  UL-TimeslotLCR-InformationList-PhyChReconfRqstTDD		PRESENCE optional }|
	--For 1.28Mcps TDD only
	{ ID id-UL-Timeslot-InformationList-PhyChReconfRqstTDD768   CRITICALITY reject		EXTENSION  UL-Timeslot-InformationList-PhyChReconfRqstTDD768		PRESENCE optional },
	--For 7.68Mcps TDD only
	...
}

UL-TimeslotLCR-InformationList-PhyChReconfRqstTDD::= SEQUENCE ( SIZE (1..maxNrOfTsLCR)) OF UL-TimeslotLCR-InformationItem-PhyChReconfRqstTDD

UL-TimeslotLCR-InformationItem-PhyChReconfRqstTDD ::= SEQUENCE {
	timeSlotLCR						TimeSlotLCR,
	midambleShiftLCR				MidambleShiftLCR		OPTIONAL,
	tFCI-Presence					TFCI-Presence		OPTIONAL,
	uL-Code-LCR-Information			TDD-UL-Code-LCR-Information		OPTIONAL,
	iE-Extensions					ProtocolExtensionContainer { {UL-TimeslotLCR-InformationItem-PhyChReconfRqstTDD-ExtIEs} } OPTIONAL,
	...
}

UL-TimeslotLCR-InformationItem-PhyChReconfRqstTDD-ExtIEs RNSAP-PROTOCOL-EXTENSION ::= {
	{ ID id-PLCCH-Information-PhyChReconfRqstTDD		CRITICALITY reject		EXTENSION PLCCHinformation		PRESENCE optional },
	...
}

UL-Timeslot-InformationList-PhyChReconfRqstTDD::= SEQUENCE ( SIZE (1..maxNrOfTS)) OF UL-Timeslot-InformationItem-PhyChReconfRqstTDD

UL-Timeslot-InformationItem-PhyChReconfRqstTDD ::= SEQUENCE {
	timeSlot						TimeSlot,
	midambleShiftAndBurstType					MidambleShiftAndBurstType		OPTIONAL,
	tFCI-Presence					TFCI-Presence		OPTIONAL,
	uL-Code-Information			TDD-UL-Code-Information		OPTIONAL,
	iE-Extensions					ProtocolExtensionContainer { {UL-Timeslot-InformationItem-PhyChReconfRqstTDD-ExtIEs} } OPTIONAL,
	...
}

UL-Timeslot-InformationItem-PhyChReconfRqstTDD-ExtIEs RNSAP-PROTOCOL-EXTENSION ::= {
	...
}

UL-Timeslot-InformationList-PhyChReconfRqstTDD768::= SEQUENCE ( SIZE (1..maxNrOfTS)) OF UL-Timeslot-InformationItem-PhyChReconfRqstTDD768

UL-Timeslot-InformationItem-PhyChReconfRqstTDD768 ::= SEQUENCE {
	timeSlot						TimeSlot,
	midambleShiftAndBurstType768	MidambleShiftAndBurstType768		OPTIONAL,
	tFCI-Presence					TFCI-Presence		OPTIONAL,
	uL-Code-Information768			TDD-UL-Code-Information768		OPTIONAL,
	iE-Extensions					ProtocolExtensionContainer { {UL-Timeslot-InformationItem-PhyChReconfRqstTDD768-ExtIEs} } OPTIONAL,
	...
}

UL-Timeslot-InformationItem-PhyChReconfRqstTDD768-ExtIEs RNSAP-PROTOCOL-EXTENSION ::= {
	...
}

DL-CCTrCH-InformationList-PhyChReconfRqstTDD 		::= ProtocolIE-Single-Container { {DL-CCTrCH-InformationListIEs-PhyChReconfRqstTDD} }

DL-CCTrCH-InformationListIEs-PhyChReconfRqstTDD RNSAP-PROTOCOL-IES ::= {
	{ ID id-DL-CCTrCH-InformationListIE-PhyChReconfRqstTDD		CRITICALITY reject	TYPE DL-CCTrCH-InformationListIE-PhyChReconfRqstTDD		PRESENCE mandatory	}
}

DL-CCTrCH-InformationListIE-PhyChReconfRqstTDD ::= SEQUENCE (SIZE (1..maxNrOfCCTrCHs)) OF DL-CCTrCH-InformationItem-PhyChReconfRqstTDD

DL-CCTrCH-InformationItem-PhyChReconfRqstTDD ::= SEQUENCE {
	cCTrCH-ID						CCTrCH-ID,
	dl-DPCH-Information				DL-DPCH-InformationList-PhyChReconfRqstTDD,
	iE-Extensions					ProtocolExtensionContainer { {DL-CCTrCH-InformationItem-PhyChReconfRqstTDD-ExtIEs} } OPTIONAL,
	...
}

DL-CCTrCH-InformationItem-PhyChReconfRqstTDD-ExtIEs RNSAP-PROTOCOL-EXTENSION ::= {
	...
}

DL-DPCH-InformationList-PhyChReconfRqstTDD ::= ProtocolIE-Single-Container {{DL-DPCH-InformationListIEs-PhyChReconfRqstTDD}}

DL-DPCH-InformationListIEs-PhyChReconfRqstTDD RNSAP-PROTOCOL-IES ::= {
	{ ID id-DL-DPCH-InformationItem-PhyChReconfRqstTDD   CRITICALITY notify	TYPE DL-DPCH-InformationItem-PhyChReconfRqstTDD		PRESENCE mandatory }
}

DL-DPCH-InformationItem-PhyChReconfRqstTDD ::= SEQUENCE {
	repetitionPeriod	RepetitionPeriod	OPTIONAL,
	repetitionLength	RepetitionLength	OPTIONAL,
	tDD-DPCHOffset	TDD-DPCHOffset	OPTIONAL,
	dL-Timeslot-InformationList-PhyChReconfRqstTDD	DL-Timeslot-InformationList-PhyChReconfRqstTDD	OPTIONAL,
	iE-Extensions	ProtocolExtensionContainer { {DL-DPCH-InformationItem-PhyChReconfRqstTDD-ExtIEs} }	OPTIONAL,
	...
}

DL-DPCH-InformationItem-PhyChReconfRqstTDD-ExtIEs RNSAP-PROTOCOL-EXTENSION ::= {
	{ ID id-DL-Timeslot-LCR-InformationList-PhyChReconfRqstTDD		CRITICALITY reject		EXTENSION DL-TimeslotLCR-InformationList-PhyChReconfRqstTDD		PRESENCE optional }|
	--For 1.28Mcps TDD only
	{ ID id-DL-Timeslot-InformationList-PhyChReconfRqstTDD768		CRITICALITY reject		EXTENSION DL-Timeslot-InformationList-PhyChReconfRqstTDD768		PRESENCE optional },
	--For 7.68Mcps TDD only
	...
}

DL-TimeslotLCR-InformationList-PhyChReconfRqstTDD::= SEQUENCE ( SIZE (1..maxNrOfTsLCR)) OF DL-TimeslotLCR-InformationItem-PhyChReconfRqstTDD

DL-TimeslotLCR-InformationItem-PhyChReconfRqstTDD ::= SEQUENCE {
	timeSlotLCR						TimeSlotLCR,
	midambleShiftLCR				MidambleShiftLCR		OPTIONAL,
	tFCI-Presence					TFCI-Presence		OPTIONAL,
	dL-Code-LCR-Information			TDD-DL-Code-LCR-Information		OPTIONAL,
	iE-Extensions					ProtocolExtensionContainer { {DL-TimeslotLCR-InformationItem-PhyChReconfRqstTDD-ExtIEs} } OPTIONAL,
	...
}

DL-TimeslotLCR-InformationItem-PhyChReconfRqstTDD-ExtIEs RNSAP-PROTOCOL-EXTENSION ::= {
	...
}

DL-Timeslot-InformationList-PhyChReconfRqstTDD::= SEQUENCE ( SIZE (1..maxNrOfTS)) OF DL-Timeslot-InformationItem-PhyChReconfRqstTDD

DL-Timeslot-InformationItem-PhyChReconfRqstTDD ::= SEQUENCE {
	timeSlot						TimeSlot,
	midambleShiftAndBurstType					MidambleShiftAndBurstType		OPTIONAL,
	tFCI-Presence					TFCI-Presence		OPTIONAL,
	dL-Code-Information			TDD-DL-Code-Information		OPTIONAL,
	iE-Extensions					ProtocolExtensionContainer { {DL-Timeslot-InformationItem-PhyChReconfRqstTDD-ExtIEs} } OPTIONAL,
	...
}

DL-Timeslot-InformationItem-PhyChReconfRqstTDD-ExtIEs RNSAP-PROTOCOL-EXTENSION ::= {
	...
}

DL-Timeslot-InformationList-PhyChReconfRqstTDD768::= SEQUENCE ( SIZE (1..maxNrOfTS)) OF DL-Timeslot-InformationItem-PhyChReconfRqstTDD768

DL-Timeslot-InformationItem-PhyChReconfRqstTDD768 ::= SEQUENCE {
	timeSlot						TimeSlot,
	midambleShiftAndBurstType768	MidambleShiftAndBurstType768		OPTIONAL,
	tFCI-Presence					TFCI-Presence		OPTIONAL,
	dL-Code-Information768			TDD-DL-Code-Information768		OPTIONAL,
	iE-Extensions					ProtocolExtensionContainer { {DL-Timeslot-InformationItem-PhyChReconfRqstTDD768-ExtIEs} } OPTIONAL,
	...
}

DL-Timeslot-InformationItem-PhyChReconfRqstTDD768-ExtIEs RNSAP-PROTOCOL-EXTENSION ::= {
	...
}

HSPDSCH-Timeslot-InformationList-PhyChReconfRqstTDD ::= SEQUENCE (SIZE (1..maxNrOfDLTs)) OF HSPDSCH-Timeslot-InformationItem-PhyChReconfRqstTDD

HSPDSCH-Timeslot-InformationItem-PhyChReconfRqstTDD::= SEQUENCE {
	timeslot										TimeSlot,
	midambleShiftAndBurstType						MidambleShiftAndBurstType,
	iE-Extensions									ProtocolExtensionContainer { { HSPDSCH-Timeslot-InformationItem-PhyChReconfRqstTDD-ExtIEs } }			OPTIONAL,
	...
}

HSPDSCH-Timeslot-InformationItem-PhyChReconfRqstTDD-ExtIEs RNSAP-PROTOCOL-EXTENSION ::= {
	...
}

HSPDSCH-Timeslot-InformationListLCR-PhyChReconfRqstTDD::= SEQUENCE (SIZE (1..maxNrOfDLTsLCR)) OF HSPDSCH-Timeslot-InformationItemLCR-PhyChReconfRqstTDD

HSPDSCH-Timeslot-InformationItemLCR-PhyChReconfRqstTDD::= SEQUENCE {
	timeslotLCR									TimeSlotLCR,
	midambleShiftLCR							MidambleShiftLCR,
	iE-Extensions								ProtocolExtensionContainer { { HSPDSCH-Timeslot-InformationItemLCR-PhyChReconfRqstTDD-ExtIEs } }			OPTIONAL,
	...
}

HSPDSCH-Timeslot-InformationItemLCR-PhyChReconfRqstTDD-ExtIEs RNSAP-PROTOCOL-EXTENSION ::= {
	...
}

HSPDSCH-Timeslot-InformationList-PhyChReconfRqstTDD768 ::= SEQUENCE (SIZE (1..maxNrOfDLTs)) OF HSPDSCH-Timeslot-InformationItem-PhyChReconfRqstTDD768

HSPDSCH-Timeslot-InformationItem-PhyChReconfRqstTDD768::= SEQUENCE {
	timeslot										TimeSlot,
	midambleShiftAndBurstType768					MidambleShiftAndBurstType768,
	iE-Extensions									ProtocolExtensionContainer { { HSPDSCH-Timeslot-InformationItem-PhyChReconfRqstTDD768-ExtIEs } }			OPTIONAL,
	...
}

HSPDSCH-Timeslot-InformationItem-PhyChReconfRqstTDD768-ExtIEs RNSAP-PROTOCOL-EXTENSION ::= {
	...
}

PhysicalChannelReconfigurationRequestTDD-Extensions RNSAP-PROTOCOL-EXTENSION ::= {
	...
}

-- **************************************************************
--
-- PHYSICAL CHANNEL RECONFIGURATION COMMAND
--
-- **************************************************************

PhysicalChannelReconfigurationCommand ::= SEQUENCE {
	protocolIEs                     ProtocolIE-Container       {{PhysicalChannelReconfigurationCommand-IEs}},
	protocolExtensions              ProtocolExtensionContainer {{PhysicalChannelReconfigurationCommand-Extensions}}                   OPTIONAL,
	...
}

PhysicalChannelReconfigurationCommand-IEs RNSAP-PROTOCOL-IES ::= {
	{ ID id-CFN					CRITICALITY ignore	TYPE CFN					PRESENCE mandatory	} |
	{ ID id-CriticalityDiagnostics			CRITICALITY ignore	TYPE CriticalityDiagnostics			PRESENCE optional	},
	...
}

PhysicalChannelReconfigurationCommand-Extensions RNSAP-PROTOCOL-EXTENSION ::= {
	...
}

-- **************************************************************
--
-- PHYSICAL CHANNEL RECONFIGURATION FAILURE
--
-- **************************************************************

PhysicalChannelReconfigurationFailure ::= SEQUENCE {
	protocolIEs                     ProtocolIE-Container       {{PhysicalChannelReconfigurationFailure-IEs}},
	protocolExtensions              ProtocolExtensionContainer {{PhysicalChannelReconfigurationFailure-Extensions}}                   OPTIONAL,
	...
}

PhysicalChannelReconfigurationFailure-IEs RNSAP-PROTOCOL-IES ::= {
	{ ID id-Cause					CRITICALITY ignore	TYPE Cause					PRESENCE mandatory	} |
	{ ID id-CriticalityDiagnostics			CRITICALITY ignore	TYPE CriticalityDiagnostics			PRESENCE optional	},
	...
}

PhysicalChannelReconfigurationFailure-Extensions RNSAP-PROTOCOL-EXTENSION ::= {
	...
}

-- **************************************************************
--
-- RADIO LINK CONGESTION INDICATION
--
-- **************************************************************

RadioLinkCongestionIndication ::= SEQUENCE {
	protocolIEs                     ProtocolIE-Container       {{RadioLinkCongestionIndication-IEs}},
	protocolExtensions              ProtocolExtensionContainer {{RadioLinkCongestionIndication-Extensions}}                   OPTIONAL,
	...
}

RadioLinkCongestionIndication-IEs RNSAP-PROTOCOL-IES ::= {
	{ ID id-CongestionCause						CRITICALITY ignore  TYPE CongestionCause						   PRESENCE optional }|
	{ ID id-RL-InformationList-RL-CongestInd	CRITICALITY ignore	TYPE RL-InformationList-RL-CongestInd		PRESENCE mandatory },
	...
}

RL-InformationList-RL-CongestInd			::= SEQUENCE (SIZE (1..maxNrOfRLs)) OF ProtocolIE-Single-Container { {RL-InformationItemIEs-RL-CongestInd} }

RL-InformationItemIEs-RL-CongestInd RNSAP-PROTOCOL-IES ::= {
	{ ID id-RL-InformationItem-RL-CongestInd		CRITICALITY ignore	TYPE RL-InformationItem-RL-CongestInd		PRESENCE mandatory	}
}

RL-InformationItem-RL-CongestInd ::= SEQUENCE {
	rL-ID								RL-ID,
	dCH-Rate-Information		DCH-Rate-Information-RL-CongestInd,
	iE-Extensions				ProtocolExtensionContainer { {RL-Information-RL-CongestInd-ExtIEs} } OPTIONAL,
	...
}

DCH-Rate-Information-RL-CongestInd ::= SEQUENCE (SIZE (1..maxNrOfDCHs)) OF ProtocolIE-Single-Container { {DCH-Rate-InformationItemIEs-RL-CongestInd} }

DCH-Rate-InformationItemIEs-RL-CongestInd RNSAP-PROTOCOL-IES ::= {
	{ ID id-DCH-Rate-InformationItem-RL-CongestInd		CRITICALITY ignore	TYPE DCH-Rate-InformationItem-RL-CongestInd		PRESENCE mandatory	}
}

DCH-Rate-InformationItem-RL-CongestInd ::= SEQUENCE {
	dCH-ID						DCH-ID,
	allowed-Rate-Information	Allowed-Rate-Information OPTIONAL,
	iE-Extensions				ProtocolExtensionContainer { {DCH-Rate-InformationItem-RL-CongestInd-ExtIEs} } OPTIONAL,
	...
}

DCH-Rate-InformationItem-RL-CongestInd-ExtIEs RNSAP-PROTOCOL-EXTENSION ::= {
	...
}

RL-Information-RL-CongestInd-ExtIEs RNSAP-PROTOCOL-EXTENSION ::= {
	{ ID id-EDCH-MacdFlowSpecificInformationList-RL-CongestInd  CRITICALITY ignore	EXTENSION EDCH-MacdFlowSpecificInformationList-RL-CongestInd PRESENCE optional }|
	{ ID id-DCH-Indicator-For-E-DCH-HSDPA-Operation		CRITICALITY ignore	EXTENSION DCH-Indicator-For-E-DCH-HSDPA-Operation										PRESENCE optional },
	...
}

RadioLinkCongestionIndication-Extensions RNSAP-PROTOCOL-EXTENSION ::= {
	...
}

EDCH-MacdFlowSpecificInformationList-RL-CongestInd	::= SEQUENCE (SIZE (1.. maxNrOfEDCHMACdFlows)) OF ProtocolIE-Single-Container { {EDCH-MacdFlowSpecificInformationItemIEs-RL-CongestInd} }

EDCH-MacdFlowSpecificInformationItemIEs-RL-CongestInd RNSAP-PROTOCOL-IES ::= {
	{ ID id-EDCH-MacdFlowSpecificInformationItem-RL-CongestInd		CRITICALITY ignore	TYPE EDCH-MacdFlowSpecificInformationItem-RL-CongestInd	PRESENCE mandatory	}
}

EDCH-MacdFlowSpecificInformationItem-RL-CongestInd ::= SEQUENCE {
	eDCH-MACdFlow-ID			EDCH-MACdFlow-ID,
	iE-Extensions				ProtocolExtensionContainer { { EDCH-MacdFlowSpecificInformation-RL-CongestInd-ExtIEs} } OPTIONAL,
	...
}

EDCH-MacdFlowSpecificInformation-RL-CongestInd-ExtIEs RNSAP-PROTOCOL-EXTENSION ::= {
	...
}

-- **************************************************************
--
-- UPLINK SIGNALLING TRANSFER INDICATION FDD
--
-- **************************************************************

UplinkSignallingTransferIndicationFDD ::= SEQUENCE {
	protocolIEs                     ProtocolIE-Container       {{UplinkSignallingTransferIndicationFDD-IEs}},
	protocolExtensions              ProtocolExtensionContainer {{UplinkSignallingTransferIndicationFDD-Extensions}}                   OPTIONAL,
	...
}

UplinkSignallingTransferIndicationFDD-IEs RNSAP-PROTOCOL-IES ::= {
	{ ID id-UC-ID	CRITICALITY ignore	TYPE UC-ID	PRESENCE mandatory	} |
	{ ID id-SAI	CRITICALITY ignore	TYPE SAI	PRESENCE mandatory	} |
	{ ID id-GA-Cell	CRITICALITY ignore	TYPE GA-Cell	PRESENCE optional	} |
	{ ID id-C-RNTI	CRITICALITY ignore	TYPE C-RNTI	PRESENCE mandatory	} |
	{ ID id-S-RNTI	CRITICALITY ignore	TYPE S-RNTI	PRESENCE mandatory	} |
	{ ID id-D-RNTI	CRITICALITY ignore	TYPE D-RNTI	PRESENCE optional	} |
	{ ID id-PropagationDelay	CRITICALITY ignore	TYPE PropagationDelay	PRESENCE mandatory	} |
	{ ID id-STTD-SupportIndicator	CRITICALITY ignore 	TYPE STTD-SupportIndicator	PRESENCE mandatory } |
	{ ID id-ClosedLoopMode1-SupportIndicator	CRITICALITY ignore 	TYPE ClosedLoopMode1-SupportIndicator	PRESENCE mandatory } |
	{ ID id-L3-Information	CRITICALITY ignore	TYPE L3-Information	PRESENCE mandatory	} |
	{ ID id-CN-PS-DomainIdentifier	CRITICALITY ignore	TYPE CN-PS-DomainIdentifier	PRESENCE optional	} |
	{ ID id-CN-CS-DomainIdentifier	CRITICALITY ignore	TYPE CN-CS-DomainIdentifier	PRESENCE optional	} |
	{ ID id-URA-Information	CRITICALITY ignore	TYPE URA-Information	PRESENCE optional	},
	...
}

UplinkSignallingTransferIndicationFDD-Extensions RNSAP-PROTOCOL-EXTENSION ::= {
	{ ID id-GA-CellAdditionalShapes	CRITICALITY ignore	EXTENSION GA-CellAdditionalShapes	PRESENCE optional }|
	{ ID id-DPC-Mode-Change-SupportIndicator	CRITICALITY ignore	EXTENSION DPC-Mode-Change-SupportIndicator	PRESENCE optional }|
	{ ID id-CommonTransportChannelResourcesInitialisationNotRequired	CRITICALITY ignore	EXTENSION CommonTransportChannelResourcesInitialisationNotRequired	PRESENCE optional }|
	{ ID id-CellCapabilityContainer-FDD	CRITICALITY ignore	EXTENSION CellCapabilityContainer-FDD	PRESENCE optional }|
	{ ID id-SNA-Information	CRITICALITY ignore	EXTENSION SNA-Information	PRESENCE optional }|
	{ ID id-CellPortionID	CRITICALITY ignore	EXTENSION CellPortionID 	PRESENCE optional }|
	{ ID id-Active-MBMS-Bearer-ServiceFDD	CRITICALITY ignore	EXTENSION Active-MBMS-Bearer-Service-ListFDD	PRESENCE optional}|
	{ ID id-Inter-Frequency-Cell-List	CRITICALITY ignore	EXTENSION Inter-Frequency-Cell-List	PRESENCE optional }|
	{ ID id-ExtendedPropagationDelay	CRITICALITY ignore	EXTENSION ExtendedPropagationDelay	PRESENCE optional }|
	{ ID id-HSDSCH-RNTI	CRITICALITY ignore	EXTENSION HSDSCH-RNTI	PRESENCE optional }|
	{ ID id-Multiple-PLMN-List	CRITICALITY ignore	EXTENSION Multiple-PLMN-List	PRESENCE optional }|
	{ ID id-E-RNTI	CRITICALITY ignore	EXTENSION E-RNTI	PRESENCE optional }|
	{ ID id-Max-UE-DTX-Cycle	CRITICALITY ignore	EXTENSION Max-UE-DTX-Cycle	PRESENCE conditional }|
	-- This IE shall be present if the Continuous Packet Connectivity DTX-DRX Support Indicator IE in Cell Capability Container FDD IE is set to 1.
	{ ID id-CellCapabilityContainerExtension-FDD	CRITICALITY ignore	EXTENSION 	CellCapabilityContainerExtension-FDD	PRESENCE optional }|
	{ ID id-Secondary-Serving-Cell-List	CRITICALITY ignore	EXTENSION Secondary-Serving-Cell-List 	PRESENCE optional }|
	{ ID id-Dual-Band-Secondary-Serving-Cell-List	CRITICALITY ignore	EXTENSION Secondary-Serving-Cell-List 	PRESENCE optional },
	...
}

-- **************************************************************
--
-- UPLINK SIGNALLING TRANSFER INDICATION TDD
--
-- **************************************************************

UplinkSignallingTransferIndicationTDD ::= SEQUENCE {
	protocolIEs                     ProtocolIE-Container       {{UplinkSignallingTransferIndicationTDD-IEs}},
	protocolExtensions              ProtocolExtensionContainer {{UplinkSignallingTransferIndicationTDD-Extensions}}                   OPTIONAL,
	...
}

UplinkSignallingTransferIndicationTDD-IEs RNSAP-PROTOCOL-IES ::= {
	{ ID id-UC-ID	CRITICALITY ignore	TYPE UC-ID	PRESENCE mandatory } |
	{ ID id-SAI	CRITICALITY ignore	TYPE SAI	PRESENCE mandatory } |
	{ ID id-GA-Cell	CRITICALITY ignore	TYPE GA-Cell	PRESENCE optional } |
	{ ID id-C-RNTI	CRITICALITY ignore	TYPE C-RNTI	PRESENCE mandatory } |
	{ ID id-S-RNTI	CRITICALITY ignore	TYPE S-RNTI	PRESENCE mandatory } |
	{ ID id-D-RNTI	CRITICALITY ignore	TYPE D-RNTI	PRESENCE optional } |
	{ ID id-RxTimingDeviationForTA	CRITICALITY ignore 	TYPE RxTimingDeviationForTA	PRESENCE mandatory } |
	{ ID id-L3-Information	CRITICALITY ignore	TYPE L3-Information	PRESENCE mandatory } |
	{ ID id-CN-PS-DomainIdentifier	CRITICALITY ignore	TYPE CN-PS-DomainIdentifier	PRESENCE optional } |
	{ ID id-CN-CS-DomainIdentifier	CRITICALITY ignore	TYPE CN-CS-DomainIdentifier	PRESENCE optional } |
	{ ID id-URA-Information	CRITICALITY ignore	TYPE URA-Information	PRESENCE optional },
	...
}

UplinkSignallingTransferIndicationTDD-Extensions RNSAP-PROTOCOL-EXTENSION ::= {
	{ ID id-GA-CellAdditionalShapes	CRITICALITY ignore	EXTENSION GA-CellAdditionalShapes	PRESENCE optional }|
	{ ID id-CommonTransportChannelResourcesInitialisationNotRequired	CRITICALITY ignore   EXTENSION CommonTransportChannelResourcesInitialisationNotRequired		PRESENCE optional }|
	{ ID id-CellCapabilityContainer-TDD	CRITICALITY ignore	EXTENSION CellCapabilityContainer-TDD	PRESENCE optional }|
	-- Applicable to 3.84Mcps TDD only
	{ ID id-CellCapabilityContainer-TDD-LCR	CRITICALITY ignore	EXTENSION CellCapabilityContainer-TDD-LCR	PRESENCE optional }|
	-- Applicable to 1.28Mcps TDD only
	{ ID id-SNA-Information	CRITICALITY ignore	EXTENSION SNA-Information	PRESENCE optional }|
	{ ID id-Active-MBMS-Bearer-ServiceTDD	CRITICALITY ignore	EXTENSION Active-MBMS-Bearer-Service-ListTDD	PRESENCE optional }|
	{ ID id-CellCapabilityContainer-TDD768	CRITICALITY ignore	EXTENSION CellCapabilityContainer-TDD768	PRESENCE optional }|
	-- Applicable to 7.68Mcps TDD only
	{ ID id-RxTimingDeviationForTA768	CRITICALITY ignore	EXTENSION RxTimingDeviationForTA768	PRESENCE optional }|
	{ ID id-RxTimingDeviationForTAext	CRITICALITY ignore	EXTENSION RxTimingDeviationForTAext	PRESENCE optional }|
	{ ID id-Multiple-PLMN-List	CRITICALITY ignore	EXTENSION Multiple-PLMN-List	PRESENCE optional }|
	{ ID id-HSDSCH-RNTI	CRITICALITY ignore	EXTENSION HSDSCH-RNTI	PRESENCE optional }|
	{ ID id-E-RNTI	CRITICALITY ignore	EXTENSION E-RNTI	PRESENCE optional }|
	{ ID id-CellPortionLCRID	CRITICALITY ignore	EXTENSION CellPortionLCRID 	PRESENCE optional },
	...

}

-- **************************************************************
--
-- DOWNLINK SIGNALLING TRANSFER REQUEST
--
-- **************************************************************

DownlinkSignallingTransferRequest ::= SEQUENCE {
	protocolIEs                     ProtocolIE-Container       {{DownlinkSignallingTransferRequest-IEs}},
	protocolExtensions              ProtocolExtensionContainer {{DownlinkSignallingTransferRequest-Extensions}}                   OPTIONAL,
	...
}

DownlinkSignallingTransferRequest-IEs RNSAP-PROTOCOL-IES ::= {
	{ ID id-C-ID						CRITICALITY ignore	TYPE C-ID							PRESENCE mandatory } |
	-- May be a GERAN cell identifier
	{ ID id-D-RNTI						CRITICALITY ignore	TYPE D-RNTI							PRESENCE mandatory } |
	{ ID id-L3-Information				CRITICALITY ignore	TYPE L3-Information					PRESENCE mandatory } |
	{ ID id-D-RNTI-ReleaseIndication	CRITICALITY ignore	TYPE D-RNTI-ReleaseIndication			PRESENCE mandatory },
	...
}

DownlinkSignallingTransferRequest-Extensions RNSAP-PROTOCOL-EXTENSION ::= {
	{ ID id-URA-ID						CRITICALITY ignore		EXTENSION	URA-ID								PRESENCE optional}|
	{ ID id-MBMS-Bearer-Service-List	CRITICALITY	ignore		EXTENSION MBMS-Bearer-Service-List			PRESENCE optional}|
	{ ID id-Old-URA-ID					CRITICALITY	ignore		EXTENSION	URA-ID								PRESENCE optional}|
	{ ID id-SRNC-ID						CRITICALITY  ignore		EXTENSION	RNC-ID								PRESENCE conditional}|
	-- This IE shall be present if the URA-ID IE or Old URA-ID IE is present.
	{ ID id-Extended-SRNC-ID			CRITICALITY reject		EXTENSION	Extended-RNC-ID						PRESENCE optional}|
	{ ID id-Enhanced-PCH-Capability		CRITICALITY  ignore		EXTENSION	Enhanced-PCH-Capability			PRESENCE optional},
	-- FDD and 1.28Mcps TDD only
	...
}


-- **************************************************************
--
-- RELOCATION COMMIT
--
-- **************************************************************

RelocationCommit ::= SEQUENCE {
	protocolIEs                     ProtocolIE-Container       {{RelocationCommit-IEs}},
	protocolExtensions              ProtocolExtensionContainer {{RelocationCommit-Extensions}}                   OPTIONAL,
	...
}

RelocationCommit-IEs RNSAP-PROTOCOL-IES ::= {
	{ ID id-D-RNTI					CRITICALITY ignore	TYPE D-RNTI					PRESENCE optional	} |
	{ ID id-RANAP-RelocationInformation		CRITICALITY ignore	TYPE RANAP-RelocationInformation		PRESENCE optional	},
	...
}

RelocationCommit-Extensions RNSAP-PROTOCOL-EXTENSION ::= {
	...
}

-- **************************************************************
--
-- PAGING REQUEST
--
-- **************************************************************

PagingRequest ::= SEQUENCE {
	protocolIEs                     ProtocolIE-Container       {{PagingRequest-IEs}},
	protocolExtensions              ProtocolExtensionContainer {{PagingRequest-Extensions}}                   OPTIONAL,
	...
}

PagingRequest-IEs RNSAP-PROTOCOL-IES ::= {
	{ ID id-PagingArea-PagingRqst			CRITICALITY ignore	TYPE PagingArea-PagingRqst				PRESENCE mandatory	} |
	{ ID id-SRNC-ID							CRITICALITY ignore	TYPE RNC-ID								PRESENCE mandatory	} | -- May be a BSC-Id.
	{ ID id-S-RNTI							CRITICALITY ignore	TYPE S-RNTI								PRESENCE mandatory	} |
	{ ID id-IMSI							CRITICALITY ignore	TYPE IMSI								PRESENCE mandatory	} |
	{ ID id-DRXCycleLengthCoefficient		CRITICALITY ignore	TYPE DRXCycleLengthCoefficient			PRESENCE mandatory	}|
	{ ID id-CNOriginatedPage-PagingRqst		CRITICALITY ignore	TYPE CNOriginatedPage-PagingRqst		PRESENCE optional		},
	...
}

PagingArea-PagingRqst ::= CHOICE {
	uRA						URA-PagingRqst, -- May be a GRA-ID.
	cell					Cell-PagingRqst, -- UTRAN only
	...
}

URA-PagingRqst ::= SEQUENCE {
	uRA-ID						URA-ID,
	iE-Extensions				ProtocolExtensionContainer { { URAItem-PagingRqst-ExtIEs} } OPTIONAL,
	...
}

URAItem-PagingRqst-ExtIEs RNSAP-PROTOCOL-EXTENSION ::= {
	...
}

Cell-PagingRqst ::= SEQUENCE {
	c-ID						C-ID,
	iE-Extensions				ProtocolExtensionContainer { { CellItem-PagingRqst-ExtIEs} } OPTIONAL,
	...
}

CellItem-PagingRqst-ExtIEs RNSAP-PROTOCOL-EXTENSION ::= {
	...
}

CNOriginatedPage-PagingRqst::= SEQUENCE {
	pagingCause					PagingCause,
	cNDomainType				CNDomainType,
	pagingRecordType			PagingRecordType,
	iE-Extensions				ProtocolExtensionContainer { { CNOriginatedPage-PagingRqst-ExtIEs} } OPTIONAL,
	...
}

CNOriginatedPage-PagingRqst-ExtIEs RNSAP-PROTOCOL-EXTENSION ::= {
	...
}

PagingRequest-Extensions RNSAP-PROTOCOL-EXTENSION ::= {
	{ ID id-Extended-SRNC-ID			CRITICALITY reject		EXTENSION	Extended-RNC-ID				PRESENCE optional}|
	{ ID id-Enhanced-PCH-Capability		CRITICALITY ignore		EXTENSION	Enhanced-PCH-Capability	PRESENCE optional},
	-- FDD and 1.28Mcps TDD only
	...
}

-- **************************************************************
--
-- DEDICATED MEASUREMENT INITIATION REQUEST
--
-- **************************************************************

DedicatedMeasurementInitiationRequest ::= SEQUENCE {
	protocolIEs                     ProtocolIE-Container       {{DedicatedMeasurementInitiationRequest-IEs}},
	protocolExtensions              ProtocolExtensionContainer {{DedicatedMeasurementInitiationRequest-Extensions}}                   OPTIONAL,
	...
}

DedicatedMeasurementInitiationRequest-IEs RNSAP-PROTOCOL-IES ::= {
	{ ID id-MeasurementID				CRITICALITY reject	TYPE MeasurementID				PRESENCE mandatory } |
	{ ID id-DedicatedMeasurementObjectType-DM-Rqst	CRITICALITY reject	TYPE DedicatedMeasurementObjectType-DM-Rqst	PRESENCE mandatory } |

	{ ID id-DedicatedMeasurementType		CRITICALITY reject	TYPE DedicatedMeasurementType			PRESENCE mandatory } |
	{ ID id-MeasurementFilterCoefficient	CRITICALITY reject	TYPE MeasurementFilterCoefficient		PRESENCE optional } |
	{ ID id-ReportCharacteristics			CRITICALITY reject	TYPE ReportCharacteristics				PRESENCE mandatory }|
	{ ID id-CFNReportingIndicator			CRITICALITY reject	TYPE FNReportingIndicator				PRESENCE mandatory }|
	{ ID id-CFN								CRITICALITY reject	TYPE CFN								PRESENCE optional },
	...
}

DedicatedMeasurementObjectType-DM-Rqst ::= CHOICE {
	rL						RL-DM-Rqst,
	rLS						RL-Set-DM-Rqst,
	allRL					All-RL-DM-Rqst,
	allRLS					All-RL-Set-DM-Rqst,
	...
}

RL-DM-Rqst ::= SEQUENCE {
	rL-InformationList-DM-Rqst		RL-InformationList-DM-Rqst,
	iE-Extensions					ProtocolExtensionContainer { { RLItem-DM-Rqst-ExtIEs} } OPTIONAL,
	...
	}

RLItem-DM-Rqst-ExtIEs RNSAP-PROTOCOL-EXTENSION ::= {
	...
}

RL-InformationList-DM-Rqst					::= SEQUENCE (SIZE (1..maxNrOfRLs)) OF ProtocolIE-Single-Container { {RL-Information-DM-Rqst-IEs} }

RL-Information-DM-Rqst-IEs RNSAP-PROTOCOL-IES ::= {
	{ ID id-RL-InformationItem-DM-Rqst		CRITICALITY reject	TYPE RL-InformationItem-DM-Rqst			PRESENCE mandatory	}
}

RL-InformationItem-DM-Rqst ::= SEQUENCE {
	rL-ID						RL-ID,
	dPCH-ID						DPCH-ID		OPTIONAL,
	iE-Extensions					ProtocolExtensionContainer { {RL-InformationItem-DM-Rqst-ExtIEs} } OPTIONAL,
	...
}

RL-InformationItem-DM-Rqst-ExtIEs RNSAP-PROTOCOL-EXTENSION ::= {
	{ ID id-HSSICH-Info-DM-Rqst					CRITICALITY reject				EXTENSION HSSICH-Info-DM-Rqst					PRESENCE optional}|
	-- TDD only
	{ ID id-DPCH-ID768-DM-Rqst					CRITICALITY reject				EXTENSION DPCH-ID768										PRESENCE optional}|
	{ ID id-HSSICH-Info-DM-Rqst-Extension		CRITICALITY reject				EXTENSION HSSICH-Info-DM-Rqst-Extension			PRESENCE optional},
	-- Applicable for 1.28Mcps TDD only when the HS-SICH ID IE is more than 31
	...
}

HSSICH-Info-DM-Rqst ::= SEQUENCE (SIZE (1..maxNrOfHSSICHs)) OF HS-SICH-ID

HSSICH-Info-DM-Rqst-Extension ::= SEQUENCE (SIZE (1..maxNrOfHSSICHs)) OF HS-SICH-ID-Extension

RL-Set-DM-Rqst ::= SEQUENCE {
	rL-Set-InformationList-DM-Rqst	RL-Set-InformationList-DM-Rqst,
	iE-Extensions					ProtocolExtensionContainer { { RL-SetItem-DM-Rqst-ExtIEs} } OPTIONAL,
	...
	}

RL-SetItem-DM-Rqst-ExtIEs RNSAP-PROTOCOL-EXTENSION ::= {
	...
}

RL-Set-InformationList-DM-Rqst					::= SEQUENCE (SIZE (1..maxNrOfRLSets)) OF ProtocolIE-Single-Container { {RL-Set-Information-DM-Rqst-IEs} }

RL-Set-Information-DM-Rqst-IEs RNSAP-PROTOCOL-IES ::= {
	{ ID id-RL-Set-InformationItem-DM-Rqst		CRITICALITY reject	TYPE RL-Set-InformationItem-DM-Rqst			PRESENCE mandatory	}
}

RL-Set-InformationItem-DM-Rqst ::= SEQUENCE {
	rL-Set-ID						RL-Set-ID,
	iE-Extensions					ProtocolExtensionContainer { {RL-Set-InformationItem-DM-Rqst-ExtIEs} } OPTIONAL,
	...
}

RL-Set-InformationItem-DM-Rqst-ExtIEs RNSAP-PROTOCOL-EXTENSION ::= {
	...
}

All-RL-DM-Rqst ::= NULL

All-RL-Set-DM-Rqst ::= NULL

DedicatedMeasurementInitiationRequest-Extensions RNSAP-PROTOCOL-EXTENSION ::= {
	{ ID id-PartialReportingIndicator				CRITICALITY ignore	EXTENSION	PartialReportingIndicator					PRESENCE optional }|
	{ ID	id-MeasurementRecoveryBehavior			CRITICALITY ignore	EXTENSION	MeasurementRecoveryBehavior				PRESENCE optional }|
	{ ID id-AlternativeFormatReportingIndicator		CRITICALITY ignore	EXTENSION	AlternativeFormatReportingIndicator	PRESENCE optional },
	...
}

-- **************************************************************
--
-- DEDICATED MEASUREMENT INITIATION RESPONSE
--
-- **************************************************************

DedicatedMeasurementInitiationResponse ::= SEQUENCE {
	protocolIEs                     ProtocolIE-Container       {{DedicatedMeasurementInitiationResponse-IEs}},
	protocolExtensions              ProtocolExtensionContainer {{DedicatedMeasurementInitiationResponse-Extensions}}                   OPTIONAL,
	...
}

DedicatedMeasurementInitiationResponse-IEs RNSAP-PROTOCOL-IES ::= {
	{ ID id-MeasurementID							CRITICALITY ignore	TYPE MeasurementID										PRESENCE mandatory } |
	{ ID id-DedicatedMeasurementObjectType-DM-Rsp	CRITICALITY ignore	TYPE DedicatedMeasurementObjectType-DM-Rsp		PRESENCE optional } |
	{ ID id-CriticalityDiagnostics					CRITICALITY ignore	TYPE CriticalityDiagnostics							PRESENCE optional },
	...
}

DedicatedMeasurementObjectType-DM-Rsp ::= CHOICE {
	rLs						RL-DM-Rsp,
	rLS						RL-Set-DM-Rsp,
	allRL					RL-DM-Rsp,
	allRLS					RL-Set-DM-Rsp,
	...
}

RL-DM-Rsp ::= SEQUENCE {
	rL-InformationList-DM-Rsp						RL-InformationList-DM-Rsp,
	iE-Extensions					ProtocolExtensionContainer { { RLItem-DM-Rsp-ExtIEs} } OPTIONAL,
	...
}

RLItem-DM-Rsp-ExtIEs RNSAP-PROTOCOL-EXTENSION ::= {
	...
}

RL-Set-DM-Rsp ::= SEQUENCE {
	rL-Set-InformationList-DM-Rsp	RL-Set-InformationList-DM-Rsp,
	iE-Extensions					ProtocolExtensionContainer { { RL-SetItem-DM-Rsp-ExtIEs} } OPTIONAL,
	...
}

RL-SetItem-DM-Rsp-ExtIEs RNSAP-PROTOCOL-EXTENSION ::= {
	...
}

RL-InformationList-DM-Rsp					::= SEQUENCE (SIZE (1..maxNrOfRLs)) OF ProtocolIE-Single-Container { {RL-Information-DM-Rsp-IEs} }

RL-Information-DM-Rsp-IEs RNSAP-PROTOCOL-IES ::= {
	{ ID id-RL-InformationItem-DM-Rsp		CRITICALITY ignore	TYPE RL-InformationItem-DM-Rsp		PRESENCE mandatory	}
}

RL-InformationItem-DM-Rsp ::= SEQUENCE {
	rL-ID						RL-ID,
	dPCH-ID						DPCH-ID				OPTIONAL,
	dedicatedMeasurementValue	DedicatedMeasurementValue,
	cFN							CFN					OPTIONAL,
	iE-Extensions				ProtocolExtensionContainer { {RL-InformationItem-DM-Rsp-ExtIEs} }	OPTIONAL,
	...
}

RL-InformationItem-DM-Rsp-ExtIEs RNSAP-PROTOCOL-EXTENSION ::= {
	{ID id-HSSICH-Info-DM		CRITICALITY reject				EXTENSION	HS-SICH-ID		PRESENCE optional}|
	-- TDD only
	{ ID	id-multiple-DedicatedMeasurementValueList-TDD-DM-Rsp	CRITICALITY ignore	EXTENSION Multiple-DedicatedMeasurementValueList-TDD-DM-Rsp	PRESENCE optional	}|
	-- Applicable to 3.84Mcps TDD only. This list of dedicated measurement values is used for the 2nd and beyond measurements of a RL when multiple dedicated measurement values need to be reported.
	{ ID	id-multiple-DedicatedMeasurementValueList-LCR-TDD-DM-Rsp	CRITICALITY ignore	EXTENSION Multiple-DedicatedMeasurementValueList-LCR-TDD-DM-Rsp	PRESENCE optional	}|
	-- Applicable to 1.28Mcps TDD only. This list of dedicated measurement values is used for the 2nd and beyond measurements of a RL when multiple dedicated measurement values need to be reported.
	{ ID	id-multiple-HSSICHMeasurementValueList-TDD-DM-Rsp			CRITICALITY ignore	EXTENSION Multiple-HSSICHMeasurementValueList-TDD-DM-Rsp	PRESENCE optional	}|
	-- TDD only. This list of HS-SICH measurement values is used for the 2nd and beyond measurements of a RL when multiple HS-SICH measurement values need to be reported.
	{ ID	id-multiple-DedicatedMeasurementValueList-TDD768-DM-Rsp		CRITICALITY ignore	EXTENSION Multiple-DedicatedMeasurementValueList-TDD768-DM-Rsp	PRESENCE optional	}|
	-- Applicable to 7.68Mcps TDD only. This list of dedicated measurement values is used for the 2nd and beyond measurements of a RL when multiple dedicated measurement values need to be reported.
	{ ID	id-DPCH-ID768-DM-Rsp										CRITICALITY ignore	EXTENSION DPCH-ID768											PRESENCE optional}|
	{ ID id-HS-SICH-ID-Extension										CRITICALITY ignore	EXTENSION HS-SICH-ID-Extension								PRESENCE optional},
	-- Applicable for 1.28Mcps TDD only when the HS-SICH ID IE is more than 31
	...
}

RL-Set-InformationList-DM-Rsp	::= SEQUENCE (SIZE (1..maxNrOfRLSets)) OF ProtocolIE-Single-Container { {RL-Set-Information-DM-Rsp-IEs} }

RL-Set-Information-DM-Rsp-IEs RNSAP-PROTOCOL-IES ::= {
	{ ID id-RL-Set-InformationItem-DM-Rsp		CRITICALITY ignore	TYPE RL-Set-InformationItem-DM-Rsp		PRESENCE mandatory	}
}

RL-Set-InformationItem-DM-Rsp ::= SEQUENCE {
	rL-Set-ID						RL-Set-ID,
	dedicatedMeasurementValue		DedicatedMeasurementValue,
	cFN								CFN			OPTIONAL,
	iE-Extensions					ProtocolExtensionContainer { {RL-Set-InformationItem-DM-Rspns-ExtIEs} }	OPTIONAL,
	...
}

RL-Set-InformationItem-DM-Rspns-ExtIEs RNSAP-PROTOCOL-EXTENSION ::= {
	...
}

DedicatedMeasurementInitiationResponse-Extensions RNSAP-PROTOCOL-EXTENSION ::= {
	{ ID	id-MeasurementRecoverySupportIndicator		CRITICALITY ignore		EXTENSION	MeasurementRecoverySupportIndicator		PRESENCE optional
	},
	...
}

Multiple-DedicatedMeasurementValueList-TDD-DM-Rsp ::= SEQUENCE (SIZE (1.. maxNrOfDPCHsPerRL-1)) OF Multiple-DedicatedMeasurementValueItem-TDD-DM-Rsp

Multiple-DedicatedMeasurementValueItem-TDD-DM-Rsp ::= SEQUENCE {
	dPCH-ID								DPCH-ID,
	dedicatedMeasurementValue			DedicatedMeasurementValue,
	iE-Extensions						ProtocolExtensionContainer { { Multiple-DedicatedMeasurementValueItem-TDD-DM-Rsp-ExtIEs} }		OPTIONAL,
	...

}

Multiple-DedicatedMeasurementValueItem-TDD-DM-Rsp-ExtIEs RNSAP-PROTOCOL-EXTENSION ::= {
	...
}

Multiple-DedicatedMeasurementValueList-LCR-TDD-DM-Rsp ::= SEQUENCE (SIZE (1.. maxNrOfDPCHsLCRPerRL-1)) OF Multiple-DedicatedMeasurementValueItem-LCR-TDD-DM-Rsp

Multiple-DedicatedMeasurementValueItem-LCR-TDD-DM-Rsp ::= SEQUENCE {
	dPCH-ID								DPCH-ID,
	dedicatedMeasurementValue			DedicatedMeasurementValue,
	iE-Extensions						ProtocolExtensionContainer { { Multiple-DedicatedMeasurementValueItem-LCR-TDD-DM-Rsp-ExtIEs} }		OPTIONAL,
	...
}

Multiple-DedicatedMeasurementValueItem-LCR-TDD-DM-Rsp-ExtIEs RNSAP-PROTOCOL-EXTENSION ::= {
	...
}

Multiple-HSSICHMeasurementValueList-TDD-DM-Rsp ::= SEQUENCE (SIZE (1.. maxNrOfHSSICHs-1)) OF Multiple-HSSICHMeasurementValueItem-TDD-DM-Rsp

Multiple-HSSICHMeasurementValueItem-TDD-DM-Rsp ::= SEQUENCE {
	hsSICH-ID							HS-SICH-ID,
	dedicatedMeasurementValue			DedicatedMeasurementValue,
	iE-Extensions						ProtocolExtensionContainer { { Multiple-HSSICHMeasurementValueItem-TDD-DM-Rsp-ExtIEs} }		OPTIONAL,
	...
}


Multiple-HSSICHMeasurementValueItem-TDD-DM-Rsp-ExtIEs RNSAP-PROTOCOL-EXTENSION ::= {
	{ ID id-HS-SICH-ID-Extension			CRITICALITY ignore		EXTENSION HS-SICH-ID-Extension		PRESENCE optional},
	-- Applicable for 1.28Mcps TDD only when the HS-SICH ID IE is more than 31
	...
}

Multiple-DedicatedMeasurementValueList-TDD768-DM-Rsp ::= SEQUENCE (SIZE (1.. maxNrOfDPCHs768PerRL-1)) OF Multiple-DedicatedMeasurementValueItem-TDD768-DM-Rsp

Multiple-DedicatedMeasurementValueItem-TDD768-DM-Rsp ::= SEQUENCE {
	dPCH-ID768							DPCH-ID768,
	dedicatedMeasurementValue			DedicatedMeasurementValue,
	iE-Extensions						ProtocolExtensionContainer { { Multiple-DedicatedMeasurementValueItem-TDD768-DM-Rsp-ExtIEs} }		OPTIONAL,
	...

}

Multiple-DedicatedMeasurementValueItem-TDD768-DM-Rsp-ExtIEs RNSAP-PROTOCOL-EXTENSION ::= {
	...
}

-- **************************************************************
--
-- DEDICATED MEASUREMENT INITIATION FAILURE
--
-- **************************************************************

DedicatedMeasurementInitiationFailure ::= SEQUENCE {
	protocolIEs                     ProtocolIE-Container       {{DedicatedMeasurementInitiationFailure-IEs}},
	protocolExtensions              ProtocolExtensionContainer {{DedicatedMeasurementInitiationFailure-Extensions}}                   OPTIONAL,
	...
}

DedicatedMeasurementInitiationFailure-IEs RNSAP-PROTOCOL-IES ::= {
	{ ID id-MeasurementID				CRITICALITY ignore	TYPE MeasurementID				PRESENCE mandatory	} |
	{ ID id-Cause					CRITICALITY ignore	TYPE Cause					PRESENCE mandatory	} |
	{ ID id-CriticalityDiagnostics			CRITICALITY ignore	TYPE CriticalityDiagnostics			PRESENCE optional	},
	...
}

DedicatedMeasurementInitiationFailure-Extensions RNSAP-PROTOCOL-EXTENSION ::= {
	{ ID id-DedicatedMeasurementObjectType-DM-Fail	CRITICALITY ignore	EXTENSION DedicatedMeasurementObjectType-DM-Fail	PRESENCE optional	},
	...
}

DedicatedMeasurementObjectType-DM-Fail ::= CHOICE {
	rL						RL-DM-Fail,
	rLS						RL-Set-DM-Fail,
	allRL					RL-DM-Fail,
	allRLS					RL-Set-DM-Fail,
	...
}

RL-DM-Fail ::= SEQUENCE {
	rL-unsuccessful-InformationRespList-DM-Fail		RL-Unsuccessful-InformationRespList-DM-Fail,
	rL-successful-InformationRespList-DM-Fail		RL-Successful-InformationRespList-DM-Fail			OPTIONAL,
	iE-Extensions					ProtocolExtensionContainer { { RLItem-DM-Fail-ExtIEs} } OPTIONAL,
	...
}

RLItem-DM-Fail-ExtIEs RNSAP-PROTOCOL-EXTENSION ::= {
	...
}

RL-Set-DM-Fail ::= SEQUENCE {
	rL-Set-unsuccessful-InformationRespList-DM-Fail	RL-Set-Unsuccessful-InformationRespList-DM-Fail,
	rL-Set-successful-InformationRespList-DM-Fail	RL-Set-Successful-InformationRespList-DM-Fail			OPTIONAL,
	iE-Extensions					ProtocolExtensionContainer { { RL-SetItem-DM-Fail-ExtIEs} } OPTIONAL,
	...
}

RL-SetItem-DM-Fail-ExtIEs RNSAP-PROTOCOL-EXTENSION ::= {
	...
}

RL-Unsuccessful-InformationRespList-DM-Fail			::= SEQUENCE (SIZE (1..maxNrOfRLs)) OF ProtocolIE-Single-Container { {RL-Unsuccessful-InformationResp-DM-Fail-IEs} }

RL-Unsuccessful-InformationResp-DM-Fail-IEs RNSAP-PROTOCOL-IES ::= {
	{ ID id-RL-Unsuccessful-InformationItem-DM-Fail		CRITICALITY ignore	TYPE RL-Unsuccessful-InformationItem-DM-Fail		PRESENCE mandatory	}
}

RL-Unsuccessful-InformationItem-DM-Fail ::= SEQUENCE {
	rL-ID						RL-ID,
	individualcause				Cause	OPTIONAL,
	iE-Extensions				ProtocolExtensionContainer { {RL-Unsuccessful-InformationItem-DM-Fail-ExtIEs} } OPTIONAL,
	...
}

RL-Unsuccessful-InformationItem-DM-Fail-ExtIEs RNSAP-PROTOCOL-EXTENSION ::= {
	...
}

RL-Successful-InformationRespList-DM-Fail			::= SEQUENCE (SIZE (1..maxNrOfRLs-1)) OF ProtocolIE-Single-Container { {RL-Successful-InformationResp-DM-Fail-IEs} }

RL-Successful-InformationResp-DM-Fail-IEs RNSAP-PROTOCOL-IES ::= {
	{ ID id-RL-Successful-InformationItem-DM-Fail		CRITICALITY ignore	TYPE RL-Successful-InformationItem-DM-Fail		PRESENCE mandatory	}
}

RL-Successful-InformationItem-DM-Fail ::= SEQUENCE {
	rL-ID						RL-ID,
	dPCH-ID						DPCH-ID				OPTIONAL,
	dedicatedMeasurementValue	DedicatedMeasurementValue,
	cFN							CFN					OPTIONAL,
	iE-Extensions				ProtocolExtensionContainer { {RL-Successful-InformationItem-DM-Fail-ExtIEs} } OPTIONAL,
	...
}

RL-Successful-InformationItem-DM-Fail-ExtIEs RNSAP-PROTOCOL-EXTENSION ::= {
	{ID id-HSSICH-Info-DM					CRITICALITY reject				EXTENSION	HS-SICH-ID		PRESENCE optional}|
	-- TDD only
	{ ID id-HS-SICH-ID-Extension			CRITICALITY ignore				EXTENSION HS-SICH-ID-Extension			PRESENCE optional},
	-- Applicable for 1.28Mcps TDD only when the HS-SICH ID IE is more than 31
	...
}

RL-Set-Unsuccessful-InformationRespList-DM-Fail				::= SEQUENCE (SIZE (1..maxNrOfRLSets)) OF ProtocolIE-Single-Container { {RL-Set-Unsuccessful-InformationResp-DM-Fail-IEs} }

RL-Set-Unsuccessful-InformationResp-DM-Fail-IEs RNSAP-PROTOCOL-IES ::= {
	{ ID id-RL-Set-Unsuccessful-InformationItem-DM-Fail		CRITICALITY ignore	TYPE RL-Set-Unsuccessful-InformationItem-DM-Fail		PRESENCE mandatory	}
}

RL-Set-Unsuccessful-InformationItem-DM-Fail ::= SEQUENCE {
	rL-Set-ID						RL-Set-ID,
	individualcause					Cause		OPTIONAL,
	iE-Extensions					ProtocolExtensionContainer { {RL-Set-Unsuccessful-InformationItem-DM-Failns-ExtIEs} } OPTIONAL,
	...
}

RL-Set-Unsuccessful-InformationItem-DM-Failns-ExtIEs RNSAP-PROTOCOL-EXTENSION ::= {
	...
}

RL-Set-Successful-InformationRespList-DM-Fail				::= SEQUENCE (SIZE (1..maxNrOfRLSets-1)) OF ProtocolIE-Single-Container { {RL-Set-Successful-InformationResp-DM-Fail-IEs} }

RL-Set-Successful-InformationResp-DM-Fail-IEs RNSAP-PROTOCOL-IES ::= {
	{ ID id-RL-Set-Successful-InformationItem-DM-Fail		CRITICALITY ignore	TYPE RL-Set-Successful-InformationItem-DM-Fail		PRESENCE mandatory	}
}

RL-Set-Successful-InformationItem-DM-Fail ::= SEQUENCE {
	rL-Set-ID						RL-Set-ID,
	dedicatedMeasurementValue		DedicatedMeasurementValue,
	cFN								CFN					OPTIONAL,
	iE-Extensions					ProtocolExtensionContainer { {RL-Set-Successful-InformationItem-DM-Failns-ExtIEs} }	OPTIONAL,
	...
}

RL-Set-Successful-InformationItem-DM-Failns-ExtIEs RNSAP-PROTOCOL-EXTENSION ::= {
	...
}

-- **************************************************************
--
-- DEDICATED MEASUREMENT REPORT
--
-- **************************************************************

DedicatedMeasurementReport ::= SEQUENCE {
	protocolIEs                     ProtocolIE-Container       {{DedicatedMeasurementReport-IEs}},
	protocolExtensions              ProtocolExtensionContainer {{DedicatedMeasurementReport-Extensions}}                   OPTIONAL,
	...
}

DedicatedMeasurementReport-IEs RNSAP-PROTOCOL-IES ::= {
	{ ID id-MeasurementID				CRITICALITY ignore	TYPE MeasurementID				PRESENCE mandatory	} |
	{ ID id-DedicatedMeasurementObjectType-DM-Rprt	CRITICALITY ignore	TYPE DedicatedMeasurementObjectType-DM-Rprt	PRESENCE mandatory	},
	...
}

DedicatedMeasurementObjectType-DM-Rprt ::= CHOICE {
	rLs						RL-DM-Rprt,
	rLS						RL-Set-DM-Rprt,
	allRL					RL-DM-Rprt,
	allRLS					RL-Set-DM-Rprt,
	...
}

RL-DM-Rprt ::= SEQUENCE {
	rL-InformationList-DM-Rprt		RL-InformationList-DM-Rprt,
	iE-Extensions					ProtocolExtensionContainer { { RLItem-DM-Rprt-ExtIEs} } OPTIONAL,
	...
}

RLItem-DM-Rprt-ExtIEs RNSAP-PROTOCOL-EXTENSION ::= {
	...
}

RL-Set-DM-Rprt ::= SEQUENCE {
	rL-Set-InformationList-DM-Rprt	RL-Set-InformationList-DM-Rprt,
	iE-Extensions					ProtocolExtensionContainer { { RL-SetItem-DM-Rprt-ExtIEs} } OPTIONAL,
	...
}

RL-SetItem-DM-Rprt-ExtIEs RNSAP-PROTOCOL-EXTENSION ::= {
	...
}

RL-InformationList-DM-Rprt					::= SEQUENCE (SIZE (1..maxNrOfRLs)) OF ProtocolIE-Single-Container { {RL-Information-DM-Rprt-IEs} }

RL-Information-DM-Rprt-IEs RNSAP-PROTOCOL-IES ::= {
	{ ID id-RL-InformationItem-DM-Rprt		CRITICALITY ignore	TYPE RL-InformationItem-DM-Rprt			PRESENCE mandatory	}
}

RL-InformationItem-DM-Rprt ::= SEQUENCE {
	rL-ID						RL-ID,
	dPCH-ID						DPCH-ID				OPTIONAL,
	dedicatedMeasurementValueInformation	DedicatedMeasurementValueInformation,
	iE-Extensions					ProtocolExtensionContainer { {RL-InformationItem-DM-Rprt-ExtIEs} } OPTIONAL,
	...
}

RL-InformationItem-DM-Rprt-ExtIEs RNSAP-PROTOCOL-EXTENSION ::= {
	{ID id-HSSICH-Info-DM-Rprt		CRITICALITY ignore				EXTENSION	HS-SICH-ID		PRESENCE optional}|
	-- TDD only
	{ ID	id-DPCH-ID768-DM-Rprt		CRITICALITY ignore				EXTENSION	DPCH-ID768		PRESENCE optional}|
	{ ID id-HS-SICH-ID-Extension		CRITICALITY ignore				EXTENSION HS-SICH-ID-Extension					PRESENCE optional},
	-- Applicable for 1.28Mcps TDD only when the HS-SICH ID IE is more than 31
	...
}

RL-Set-InformationList-DM-Rprt					::= SEQUENCE (SIZE (1..maxNrOfRLSets)) OF ProtocolIE-Single-Container { {RL-Set-Information-DM-Rprt-IEs} }

RL-Set-Information-DM-Rprt-IEs RNSAP-PROTOCOL-IES ::= {
	{ ID id-RL-Set-InformationItem-DM-Rprt		CRITICALITY ignore	TYPE RL-Set-InformationItem-DM-Rprt			PRESENCE mandatory	}
}

RL-Set-InformationItem-DM-Rprt ::= SEQUENCE {
	rL-Set-ID						RL-Set-ID,
	dedicatedMeasurementValueInformation	DedicatedMeasurementValueInformation,
	iE-Extensions					ProtocolExtensionContainer { {RL-Set-InformationItem-DM-Rprt-ExtIEs} } OPTIONAL,
	...
}

RL-Set-InformationItem-DM-Rprt-ExtIEs RNSAP-PROTOCOL-EXTENSION ::= {
	...
}

DedicatedMeasurementReport-Extensions RNSAP-PROTOCOL-EXTENSION ::= {
	{ ID	id-MeasurementRecoveryReportingIndicator		CRITICALITY ignore		EXTENSION	MeasurementRecoveryReportingIndicator		PRESENCE optional },
	...
}

-- **************************************************************
--
-- DEDICATED MEASUREMENT TERMINATION REQUEST
--
-- **************************************************************

DedicatedMeasurementTerminationRequest ::= SEQUENCE {
	protocolIEs                     ProtocolIE-Container       {{DedicatedMeasurementTerminationRequest-IEs}},
	protocolExtensions              ProtocolExtensionContainer {{DedicatedMeasurementTerminationRequest-Extensions}}                   OPTIONAL,
	...
}

DedicatedMeasurementTerminationRequest-IEs RNSAP-PROTOCOL-IES ::= {
	{ ID id-MeasurementID				CRITICALITY ignore	TYPE MeasurementID				PRESENCE mandatory	},
	...
}

DedicatedMeasurementTerminationRequest-Extensions RNSAP-PROTOCOL-EXTENSION ::= {
	...
}

-- **************************************************************
--
-- DEDICATED MEASUREMENT FAILURE INDICATION
--
-- **************************************************************

DedicatedMeasurementFailureIndication ::= SEQUENCE {
	protocolIEs                     ProtocolIE-Container       {{DedicatedMeasurementFailureIndication-IEs}},
	protocolExtensions              ProtocolExtensionContainer {{DedicatedMeasurementFailureIndication-Extensions}}                   OPTIONAL,
	...
}

DedicatedMeasurementFailureIndication-IEs RNSAP-PROTOCOL-IES ::= {
	{ ID id-MeasurementID				CRITICALITY ignore	TYPE MeasurementID				PRESENCE mandatory	} |
	{ ID id-Cause					CRITICALITY ignore	TYPE Cause					PRESENCE mandatory	},
	...
}

DedicatedMeasurementFailureIndication-Extensions RNSAP-PROTOCOL-EXTENSION ::= {
	{ ID id-DedicatedMeasurementObjectType-DM-Fail-Ind	CRITICALITY ignore	EXTENSION DedicatedMeasurementObjectType-DM-Fail-Ind	PRESENCE optional	},
	...
}

DedicatedMeasurementObjectType-DM-Fail-Ind ::= CHOICE {
	rL						RL-DM-Fail-Ind,
	rLS						RL-Set-DM-Fail-Ind,
	allRL					RL-DM-Fail-Ind,
	allRLS					RL-Set-DM-Fail-Ind,
	...
}

RL-DM-Fail-Ind ::= SEQUENCE {
	rL-unsuccessful-InformationRespList-DM-Fail-Ind		RL-Unsuccessful-InformationRespList-DM-Fail-Ind,
	iE-Extensions										ProtocolExtensionContainer { { RLItem-DM-Fail-Ind-ExtIEs} } OPTIONAL,
	...
}

RLItem-DM-Fail-Ind-ExtIEs RNSAP-PROTOCOL-EXTENSION ::= {
	...
}

RL-Set-DM-Fail-Ind ::= SEQUENCE {
	rL-Set-unsuccessful-InformationRespList-DM-Fail-Ind		RL-Set-Unsuccessful-InformationRespList-DM-Fail-Ind,
	iE-Extensions											ProtocolExtensionContainer { { RL-SetItem-DM-Fail-Ind-ExtIEs} } OPTIONAL,
	...
}

RL-SetItem-DM-Fail-Ind-ExtIEs RNSAP-PROTOCOL-EXTENSION ::= {
	...
}

RL-Unsuccessful-InformationRespList-DM-Fail-Ind			::= SEQUENCE (SIZE (1..maxNrOfRLs)) OF ProtocolIE-Single-Container { {RL-Unsuccessful-InformationResp-DM-Fail-Ind-IEs} }

RL-Unsuccessful-InformationResp-DM-Fail-Ind-IEs RNSAP-PROTOCOL-IES ::= {
	{ ID id-RL-Unsuccessful-InformationItem-DM-Fail-Ind		CRITICALITY ignore	TYPE RL-Unsuccessful-InformationItem-DM-Fail-Ind		PRESENCE mandatory	}
}

RL-Unsuccessful-InformationItem-DM-Fail-Ind ::= SEQUENCE {
	rL-ID						RL-ID,
	individualcause				Cause		OPTIONAL,
	iE-Extensions				ProtocolExtensionContainer { {RL-Unsuccessful-InformationItem-DM-Fail-Ind-ExtIEs} } OPTIONAL,
	...
}

RL-Unsuccessful-InformationItem-DM-Fail-Ind-ExtIEs RNSAP-PROTOCOL-EXTENSION ::= {
	...
}

RL-Set-Unsuccessful-InformationRespList-DM-Fail-Ind				::= SEQUENCE (SIZE (1..maxNrOfRLSets)) OF ProtocolIE-Single-Container { {RL-Set-Unsuccessful-InformationResp-DM-Fail-Ind-IEs} }

RL-Set-Unsuccessful-InformationResp-DM-Fail-Ind-IEs RNSAP-PROTOCOL-IES ::= {
	{ ID id-RL-Set-Unsuccessful-InformationItem-DM-Fail-Ind		CRITICALITY ignore	TYPE RL-Set-Unsuccessful-InformationItem-DM-Fail-Ind		PRESENCE mandatory	}
}

RL-Set-Unsuccessful-InformationItem-DM-Fail-Ind ::= SEQUENCE {
	rL-Set-ID						RL-Set-ID,
	individualcause					Cause		OPTIONAL,
	iE-Extensions					ProtocolExtensionContainer { {RL-Set-Unsuccessful-InformationItem-DM-Fail-Indns-ExtIEs} } OPTIONAL,
	...
}

RL-Set-Unsuccessful-InformationItem-DM-Fail-Indns-ExtIEs RNSAP-PROTOCOL-EXTENSION ::= {
	...
}

-- **************************************************************
--
-- COMMON TRANSPORT CHANNEL RESOURCES RELEASE REQUEST
--
-- **************************************************************

CommonTransportChannelResourcesReleaseRequest ::= SEQUENCE {
	protocolIEs                     ProtocolIE-Container       {{CommonTransportChannelResourcesReleaseRequest-IEs}},
	protocolExtensions              ProtocolExtensionContainer {{CommonTransportChannelResourcesReleaseRequest-Extensions}}                   OPTIONAL,
	...
}

CommonTransportChannelResourcesReleaseRequest-IEs RNSAP-PROTOCOL-IES ::= {
	{ ID id-D-RNTI					CRITICALITY ignore	TYPE D-RNTI					PRESENCE mandatory	},
	...
}

CommonTransportChannelResourcesReleaseRequest-Extensions RNSAP-PROTOCOL-EXTENSION ::= {
	...
}

-- **************************************************************
--
-- COMMON TRANSPORT CHANNEL RESOURCES REQUEST
--
-- **************************************************************

CommonTransportChannelResourcesRequest ::= SEQUENCE {
	protocolIEs                     ProtocolIE-Container       {{CommonTransportChannelResourcesRequest-IEs}},
	protocolExtensions              ProtocolExtensionContainer {{CommonTransportChannelResourcesRequest-Extensions}}			OPTIONAL,
	...
}

CommonTransportChannelResourcesRequest-IEs RNSAP-PROTOCOL-IES ::= {
	{ ID id-D-RNTI	CRITICALITY reject	TYPE D-RNTI	PRESENCE mandatory } |
	{ ID id-C-ID	CRITICALITY reject	TYPE C-ID	PRESENCE optional } |
	{ ID id-TransportBearerRequestIndicator	CRITICALITY reject	TYPE TransportBearerRequestIndicator	PRESENCE mandatory } |
	{ ID id-TransportBearerID	CRITICALITY reject	TYPE TransportBearerID	PRESENCE mandatory },
	...
}

CommonTransportChannelResourcesRequest-Extensions RNSAP-PROTOCOL-EXTENSION ::= {
	{ ID id-Permanent-NAS-UE-Identity	CRITICALITY ignore	EXTENSION Permanent-NAS-UE-Identity	PRESENCE optional }|
	{ ID id-BindingID	CRITICALITY ignore	EXTENSION BindingID	PRESENCE optional }|
	-- Shall be ignored if bearer establishment with ALCAP.
	{ ID id-TransportLayerAddress	CRITICALITY ignore	EXTENSION TransportLayerAddress	PRESENCE optional }|
	-- Shall be ignored if bearer establishment with ALCAP.
	{ ID id-MBMS-Bearer-Service-List	CRITICALITY notify	EXTENSION MBMS-Bearer-Service-List	PRESENCE optional }|
	{ ID id-TnlQos	CRITICALITY ignore	EXTENSION TnlQos	PRESENCE optional }|
	{ ID id-Enhanced-FACH-Support-Indicator	CRITICALITY ignore	EXTENSION Enhanced-FACH-Support-Indicator	PRESENCE optional }|
	 -- FDD and 1.28Mcps TDD only
	{ ID id-Common-EDCH-Support-Indicator	CRITICALITY ignore	EXTENSION Common-EDCH-Support-Indicator	PRESENCE optional }|
	 -- FDD only
	{ ID id-HSDSCH-Physical-Layer-Category	CRITICALITY ignore	EXTENSION HSDSCH-Physical-Layer-Category	PRESENCE optional }|
	{ ID id-UE-with-enhanced-HS-SCCH-support-indicator CRITICALITY ignore EXTENSION NULL	PRESENCE optional },
	...
}

-- **************************************************************
--
-- COMMON TRANSPORT CHANNEL RESOURCES RESPONSE FDD
--
-- **************************************************************

CommonTransportChannelResourcesResponseFDD ::= SEQUENCE {
	protocolIEs                     ProtocolIE-Container       {{CommonTransportChannelResourcesResponseFDD-IEs}},
	protocolExtensions              ProtocolExtensionContainer {{CommonTransportChannelResourcesResponseFDD-Extensions}}			OPTIONAL,
	...
}

CommonTransportChannelResourcesResponseFDD-IEs RNSAP-PROTOCOL-IES ::= {
	{ ID id-S-RNTI					CRITICALITY ignore	TYPE S-RNTI					PRESENCE mandatory	} |
	{ ID id-C-RNTI					CRITICALITY ignore	TYPE C-RNTI					PRESENCE optional	} |
	{ ID id-FACH-InfoForUESelectedS-CCPCH-CTCH-ResourceRspFDD	CRITICALITY ignore	TYPE FACH-InfoForUESelectedS-CCPCH-CTCH-ResourceRspFDD		PRESENCE mandatory	} |
	{ ID id-TransportLayerAddress			CRITICALITY ignore	TYPE TransportLayerAddress			PRESENCE optional	} |
	{ ID id-BindingID				CRITICALITY ignore	TYPE BindingID					PRESENCE optional	} |
	{ ID id-CriticalityDiagnostics			CRITICALITY ignore	TYPE CriticalityDiagnostics			PRESENCE optional	},
	...
}

FACH-InfoForUESelectedS-CCPCH-CTCH-ResourceRspFDD ::= SEQUENCE {
	fACH-FlowControlInformation		FACH-FlowControlInformation-CTCH-ResourceRspFDD,
-- If the Enhanced FACH Information Response IE is included in the message, the FACH Flow Control Information IE shall be ignored.
	iE-Extensions					ProtocolExtensionContainer { {FACH-InfoForUESelectedS-CCPCH-CTCH-ResourceRspFDD-ExtIEs} } OPTIONAL,
	...
}

FACH-InfoForUESelectedS-CCPCH-CTCH-ResourceRspFDD-ExtIEs RNSAP-PROTOCOL-EXTENSION ::= {
	...
}

FACH-FlowControlInformation-CTCH-ResourceRspFDD ::= ProtocolIE-Single-Container {{ FACH-FlowControlInformationIEs-CTCH-ResourceRspFDD }}

FACH-FlowControlInformationIEs-CTCH-ResourceRspFDD RNSAP-PROTOCOL-IES ::= {
	{ ID id-FACH-FlowControlInformation	CRITICALITY ignore	TYPE	FACH-FlowControlInformation	PRESENCE mandatory	}
}

CommonTransportChannelResourcesResponseFDD-Extensions RNSAP-PROTOCOL-EXTENSION ::= {
	{ ID id-C-ID												CRITICALITY ignore		EXTENSION C-ID															PRESENCE mandatory  }|
	{ ID id-Active-MBMS-Bearer-ServiceFDD						CRITICALITY ignore		EXTENSION Active-MBMS-Bearer-Service-ListFDD					PRESENCE optional}|
	{ ID id-Enhanced-FACH-Information-ResponseFDD				CRITICALITY ignore		EXTENSION Enhanced-FACH-Information-ResponseFDD				PRESENCE optional}|
	{ ID id-Common-EDCH-MAC-d-Flow-Specific-InformationFDD		CRITICALITY ignore		EXTENSION Common-EDCH-MAC-d-Flow-Specific-InformationFDD		PRESENCE optional}|
	{ ID id-E-RNTI	CRITICALITY ignore	EXTENSION E-RNTI	PRESENCE optional },
	...
}

-- **************************************************************
--
-- COMMON TRANSPORT CHANNEL RESOURCES RESPONSE TDD
--
-- **************************************************************

CommonTransportChannelResourcesResponseTDD ::= SEQUENCE {
	protocolIEs                     ProtocolIE-Container       {{CommonTransportChannelResourcesResponseTDD-IEs}},
	protocolExtensions              ProtocolExtensionContainer {{CommonTransportChannelResourcesResponseTDD-Extensions}}			OPTIONAL,
	...
}

CommonTransportChannelResourcesResponseTDD-IEs RNSAP-PROTOCOL-IES ::= {
	{ ID id-S-RNTI					CRITICALITY ignore	TYPE S-RNTI					PRESENCE mandatory	} |
	{ ID id-C-RNTI					CRITICALITY ignore	TYPE C-RNTI					PRESENCE optional	} |
	{ ID id-FACH-InfoForUESelectedS-CCPCH-CTCH-ResourceRspTDD	CRITICALITY ignore	TYPE FACH-InfoForUESelectedS-CCPCH-CTCH-ResourceRspTDD		PRESENCE mandatory	} |
	{ ID id-TransportLayerAddress			CRITICALITY ignore	TYPE TransportLayerAddress			PRESENCE optional	} |
	{ ID id-BindingID				CRITICALITY ignore	TYPE BindingID					PRESENCE optional	} |
	{ ID id-CriticalityDiagnostics			CRITICALITY ignore	TYPE CriticalityDiagnostics			PRESENCE optional	},
	...
}

FACH-InfoForUESelectedS-CCPCH-CTCH-ResourceRspTDD ::= SEQUENCE {
	fACH-FlowControlInformation		FACH-FlowControlInformation-CTCH-ResourceRspTDD,
	iE-Extensions					ProtocolExtensionContainer { {FACH-InfoForUESelectedS-CCPCH-CTCH-ResourceRspTDD-ExtIEs} } OPTIONAL,
	...
}

FACH-InfoForUESelectedS-CCPCH-CTCH-ResourceRspTDD-ExtIEs RNSAP-PROTOCOL-EXTENSION ::= {
	...
}

FACH-FlowControlInformation-CTCH-ResourceRspTDD ::= ProtocolIE-Single-Container {{ FACH-FlowControlInformationIEs-CTCH-ResourceRspTDD }}

FACH-FlowControlInformationIEs-CTCH-ResourceRspTDD RNSAP-PROTOCOL-IES ::= {
	{ ID id-FACH-FlowControlInformation	CRITICALITY ignore	TYPE	FACH-FlowControlInformation	PRESENCE mandatory	}
}

CommonTransportChannelResourcesResponseTDD-Extensions RNSAP-PROTOCOL-EXTENSION ::= {
	{ ID id-C-ID												CRITICALITY ignore		EXTENSION 	C-ID														PRESENCE mandatory  }|
	{ ID id-Active-MBMS-Bearer-ServiceTDD						CRITICALITY ignore		EXTENSION Active-MBMS-Bearer-Service-ListTDD					PRESENCE optional}|
	{ ID id-Enhanced-FACH-Information-ResponseLCR				CRITICALITY ignore		EXTENSION Enhanced-FACH-Information-ResponseLCR				PRESENCE optional}|
	{ ID id-Common-EDCH-MAC-d-Flow-Specific-InformationLCR		CRITICALITY ignore		EXTENSION Common-EDCH-MAC-d-Flow-Specific-InformationLCR		PRESENCE optional},
	...
}

-- **************************************************************
--
-- COMMON TRANSPORT CHANNEL RESOURCES FAILURE
--
-- **************************************************************

CommonTransportChannelResourcesFailure ::= SEQUENCE {
	protocolIEs                     ProtocolIE-Container       {{CommonTransportChannelResourcesFailure-IEs}},
	protocolExtensions              ProtocolExtensionContainer {{CommonTransportChannelResourcesFailure-Extensions}}			OPTIONAL,
	...
}

CommonTransportChannelResourcesFailure-IEs RNSAP-PROTOCOL-IES ::= {
	{ ID id-S-RNTI							CRITICALITY ignore	TYPE S-RNTI							PRESENCE mandatory } |
	{ ID id-Cause							CRITICALITY ignore	TYPE Cause							PRESENCE mandatory } |
	{ ID id-CriticalityDiagnostics			CRITICALITY ignore	TYPE CriticalityDiagnostics			PRESENCE optional },
	...
}

CommonTransportChannelResourcesFailure-Extensions RNSAP-PROTOCOL-EXTENSION ::= {
	...
}

-- **************************************************************
--
-- COMPRESSED MODE COMMAND
--
-- **************************************************************

CompressedModeCommand ::= SEQUENCE {
	protocolIEs                     ProtocolIE-Container       {{CompressedModeCommand-IEs}},
	protocolExtensions              ProtocolExtensionContainer {{CompressedModeCommand-Extensions}}                   OPTIONAL,
	...
}

CompressedModeCommand-IEs RNSAP-PROTOCOL-IES ::= {
	{ ID id-Active-Pattern-Sequence-Information		CRITICALITY ignore	TYPE Active-Pattern-Sequence-Information		 PRESENCE mandatory  },
	...
}

CompressedModeCommand-Extensions RNSAP-PROTOCOL-EXTENSION ::= {
	...
}

-- **************************************************************
--
-- ERROR INDICATION
--
-- **************************************************************

ErrorIndication ::= SEQUENCE {
	protocolIEs                     ProtocolIE-Container       {{ErrorIndication-IEs}},
	protocolExtensions              ProtocolExtensionContainer {{ErrorIndication-Extensions}}                   	OPTIONAL,
	...
}

ErrorIndication-IEs RNSAP-PROTOCOL-IES ::= {
	{ ID id-Cause					CRITICALITY ignore	TYPE Cause					PRESENCE optional} |
	{ ID id-CriticalityDiagnostics			CRITICALITY ignore	TYPE CriticalityDiagnostics			PRESENCE optional	},
	...
}

ErrorIndication-Extensions RNSAP-PROTOCOL-EXTENSION ::= {
	{ ID id-S-RNTI					CRITICALITY ignore	EXTENSION S-RNTI					PRESENCE optional	} |
	{ ID id-D-RNTI					CRITICALITY ignore	EXTENSION D-RNTI					PRESENCE optional	},
	...
}

-- **************************************************************
--
-- COMMON MEASUREMENT INITIATION REQUEST
--
-- **************************************************************

CommonMeasurementInitiationRequest ::= SEQUENCE {
	protocolIEs				ProtocolIE-Container	{{CommonMeasurementInitiationRequest-IEs}},
	protocolExtensions		ProtocolExtensionContainer	{{CommonMeasurementInitiationRequest-Extensions}}		OPTIONAL,
	...
}

CommonMeasurementInitiationRequest-IEs RNSAP-PROTOCOL-IES ::= {
	{ ID id-MeasurementID					CRITICALITY	reject	TYPE	MeasurementID										PRESENCE mandatory }|
	{ ID id-CommonMeasurementObjectType-CM-Rqst	CRITICALITY	reject	TYPE	CommonMeasurementObjectType-CM-Rqst		PRESENCE mandatory }|
	{ ID id-CommonMeasurementType			CRITICALITY	reject	TYPE	CommonMeasurementType								PRESENCE mandatory }|
	{ ID id-MeasurementFilterCoefficient	CRITICALITY	reject	TYPE	MeasurementFilterCoefficient						PRESENCE optional }|
	-- UTRAN only
	{ ID id-ReportCharacteristics			CRITICALITY	reject	TYPE	ReportCharacteristics								PRESENCE mandatory }|
	{ ID id-SFNReportingIndicator			CRITICALITY	reject	TYPE	FNReportingIndicator								PRESENCE mandatory } |
	{ ID id-SFN								CRITICALITY reject	TYPE	SFN													PRESENCE optional }|
	-- UTRAN only
	{ ID id-CommonMeasurementAccuracy		CRITICALITY reject	TYPE	CommonMeasurementAccuracy							PRESENCE optional },
	-- UTRAN only
	...
}

CommonMeasurementInitiationRequest-Extensions RNSAP-PROTOCOL-EXTENSION ::= {
	{ ID	id-MeasurementRecoveryBehavior				CRITICALITY ignore				EXTENSION	MeasurementRecoveryBehavior		PRESENCE optional
	}|
	-- UTRAN only
	{ ID id-GANSS-Time-ID							CRITICALITY ignore				EXTENSION 	GANSS-Time-ID							PRESENCE optional},
	...
}

CommonMeasurementObjectType-CM-Rqst ::= CHOICE {
	cell							Cell-CM-Rqst,
	...
}

Cell-CM-Rqst ::= SEQUENCE {
	uC-ID							UC-ID,
	-- May be a GERAN cell identifier
	timeSlot						TimeSlot		OPTIONAL,	--3.84Mcps TDD and 7.68Mcps TDD only
	timeSlotLCR						TimeSlotLCR		OPTIONAL,	--1.28Mcps TDD only
	neighbouringCellMeasurementInformation			NeighbouringCellMeasurementInfo		OPTIONAL,
	-- UTRAN only
	iE-Extensions					ProtocolExtensionContainer  { { CellItem-CM-Rqst-ExtIEs} }		OPTIONAL,
	...
}

NeighbouringCellMeasurementInfo ::=	SEQUENCE (SIZE (1..maxNrOfMeasNCell)) OF
		CHOICE {
				neighbouringFDDCellMeasurementInformation		NeighbouringFDDCellMeasurementInformation,
				neighbouringTDDCellMeasurementInformation		NeighbouringTDDCellMeasurementInformation,
				...,
				extension-neighbouringCellMeasurementInformation	Extension-neighbouringCellMeasurementInformation,
				extension-neighbouringCellMeasurementInformation768	Extension-neighbouringCellMeasurementInformation768
			}

Extension-neighbouringCellMeasurementInformation	::=	ProtocolIE-Single-Container {{ Extension-neighbouringCellMeasurementInformationIE }}

Extension-neighbouringCellMeasurementInformationIE RNSAP-PROTOCOL-IES ::= {
	{ ID id-neighbouringTDDCellMeasurementInformationLCR	CRITICALITY reject	TYPE NeighbouringTDDCellMeasurementInformationLCR	PRESENCE mandatory },
	...
}


Extension-neighbouringCellMeasurementInformation768	::=	ProtocolIE-Single-Container {{ Extension-neighbouringCellMeasurementInformation768IE }}

Extension-neighbouringCellMeasurementInformation768IE RNSAP-PROTOCOL-IES ::= {
	{ ID id-neighbouringTDDCellMeasurementInformation768	CRITICALITY reject	TYPE NeighbouringTDDCellMeasurementInformation768	PRESENCE mandatory },
	...
}

CellItem-CM-Rqst-ExtIEs RNSAP-PROTOCOL-EXTENSION ::= {
	{ ID id-UARFCNforNt					CRITICALITY ignore	EXTENSION UARFCN				PRESENCE optional }|
	-- Applicable to 1.28Mcps TDD only
	{ ID id-UPPCHPositionLCR			CRITICALITY reject	EXTENSION UPPCHPositionLCR		PRESENCE optional},
	-- Applicable to 1.28Mcps TDD only
	...
}

-- **************************************************************
--
-- COMMON MEASUREMENT INITIATION RESPONSE
--
-- **************************************************************

CommonMeasurementInitiationResponse ::= SEQUENCE {
	protocolIEs				ProtocolIE-Container	{{CommonMeasurementInitiationResponse-IEs}},
	protocolExtensions		ProtocolExtensionContainer	{{CommonMeasurementInitiationResponse-Extensions}}		OPTIONAL,
	...
}

CommonMeasurementInitiationResponse-IEs RNSAP-PROTOCOL-IES ::= {
	{ ID	id-MeasurementID						CRITICALITY	ignore	TYPE	MeasurementID										PRESENCE mandatory }|
	{ ID	id-CommonMeasurementObjectType-CM-Rsp	CRITICALITY	ignore	TYPE	CommonMeasurementObjectType-CM-Rsp			PRESENCE optional }|
	{ ID	id-SFN									CRITICALITY	ignore	TYPE	SFN													PRESENCE optional }|
	-- UTRAN only
	{ ID	id-CriticalityDiagnostics				CRITICALITY	ignore	TYPE	CriticalityDiagnostics							PRESENCE optional }|
	{ ID    id-CommonMeasurementAccuracy			CRITICALITY reject	TYPE	CommonMeasurementAccuracy						PRESENCE optional },
	-- UTRAN only
	...
}

CommonMeasurementInitiationResponse-Extensions RNSAP-PROTOCOL-EXTENSION ::= {
	{ ID	id-MeasurementRecoverySupportIndicator		CRITICALITY ignore		EXTENSION	MeasurementRecoverySupportIndicator		PRESENCE optional
	},
	-- UTRAN only
	...
}

CommonMeasurementObjectType-CM-Rsp ::= CHOICE {
	cell						Cell-CM-Rsp,
	...
 }

Cell-CM-Rsp ::= SEQUENCE {
	commonMeasurementValue						CommonMeasurementValue,
	iE-Extensions								ProtocolExtensionContainer  { { CellItem-CM-Rsp-ExtIEs} }		OPTIONAL,
	...
 }

CellItem-CM-Rsp-ExtIEs RNSAP-PROTOCOL-EXTENSION ::= {
	...
}

-- **************************************************************
--
-- COMMON MEASUREMENT INITIATION FAILURE
--
-- **************************************************************

CommonMeasurementInitiationFailure ::= SEQUENCE {
	protocolIEs				ProtocolIE-Container	{{CommonMeasurementInitiationFailure-IEs}},
	protocolExtensions		ProtocolExtensionContainer	{{CommonMeasurementInitiationFailure-Extensions}}		OPTIONAL,
	...
}

CommonMeasurementInitiationFailure-IEs RNSAP-PROTOCOL-IES ::= {
	{ ID	id-MeasurementID				CRITICALITY		ignore			TYPE	MeasurementID					PRESENCE	mandatory }|
	{ ID	id-Cause						CRITICALITY		ignore			TYPE	Cause							PRESENCE	mandatory }|
	{ ID	id-CriticalityDiagnostics		CRITICALITY		ignore			TYPE	CriticalityDiagnostics		PRESENCE	optional },
	...
}

CommonMeasurementInitiationFailure-Extensions RNSAP-PROTOCOL-EXTENSION ::= {
	...
}

-- **************************************************************
--
-- COMMON MEASUREMENT REPORT
--
-- **************************************************************

CommonMeasurementReport ::= SEQUENCE {
	protocolIEs				ProtocolIE-Container	{{CommonMeasurementReport-IEs}},
	protocolExtensions		ProtocolExtensionContainer	{{CommonMeasurementReport-Extensions}}		OPTIONAL,
	...
}

CommonMeasurementReport-IEs RNSAP-PROTOCOL-IES ::= {
	{ ID	id-MeasurementID						CRITICALITY	ignore	TYPE	MeasurementID							PRESENCE	mandatory	}|
	{ ID	id-CommonMeasurementObjectType-CM-Rprt	CRITICALITY	ignore	TYPE	CommonMeasurementObjectType-CM-Rprt		PRESENCE	mandatory	}|
	{ ID	id-SFN									CRITICALITY	ignore	TYPE	SFN										PRESENCE	optional	},
	-- UTRAN only
	...
}

CommonMeasurementReport-Extensions RNSAP-PROTOCOL-EXTENSION ::= {
	{ ID	id-MeasurementRecoveryReportingIndicator		CRITICALITY ignore		EXTENSION	MeasurementRecoveryReportingIndicator		PRESENCE optional },
	-- UTRAN only
	...
}

CommonMeasurementObjectType-CM-Rprt ::= CHOICE {
	cell							Cell-CM-Rprt,
	...
 }

Cell-CM-Rprt ::= SEQUENCE {
	commonMeasurementValueInformation	CommonMeasurementValueInformation,
	iE-Extensions					ProtocolExtensionContainer  {{ CellItem-CM-Rprt-ExtIEs }}		OPTIONAL,
	...

 }

CellItem-CM-Rprt-ExtIEs RNSAP-PROTOCOL-EXTENSION ::= {
	...
}

-- **************************************************************
--
-- COMMON MEASUREMENT TERMINATION REQUEST
--
-- **************************************************************

CommonMeasurementTerminationRequest ::= SEQUENCE {
	protocolIEs				ProtocolIE-Container	{{CommonMeasurementTerminationRequest-IEs}},
	protocolExtensions		ProtocolExtensionContainer	{{CommonMeasurementTerminationRequest-Extensions}}		OPTIONAL,
	...
}

CommonMeasurementTerminationRequest-IEs RNSAP-PROTOCOL-IES ::= {
	{ ID	id-MeasurementID			CRITICALITY		ignore				TYPE	MeasurementID			PRESENCE	mandatory},
	...
}

CommonMeasurementTerminationRequest-Extensions RNSAP-PROTOCOL-EXTENSION ::= {
	...
}

-- **************************************************************
--
-- COMMON MEASUREMENT FAILURE INDICATION
--
-- **************************************************************

CommonMeasurementFailureIndication ::= SEQUENCE {
	protocolIEs				ProtocolIE-Container	{{CommonMeasurementFailureIndication-IEs}},
	protocolExtensions			ProtocolExtensionContainer	{{CommonMeasurementFailureIndication-Extensions}}				OPTIONAL,
	...
}

CommonMeasurementFailureIndication-IEs RNSAP-PROTOCOL-IES ::= {
	{ ID	id-MeasurementID			CRITICALITY	ignore			TYPE	MeasurementID			PRESENCE	mandatory	}|
	{ ID	id-Cause					CRITICALITY	ignore			TYPE	Cause					PRESENCE	mandatory	},
	...
}

CommonMeasurementFailureIndication-Extensions RNSAP-PROTOCOL-EXTENSION ::= {
	...
}

-- **************************************************************
--
-- INFORMATION EXCHANGE INITIATION REQUEST
--
-- **************************************************************

InformationExchangeInitiationRequest ::= SEQUENCE {
	protocolIEs				ProtocolIE-Container	{{InformationExchangeInitiationRequest-IEs}},
	protocolExtensions		ProtocolExtensionContainer	{{InformationExchangeInitiationRequest-Extensions}}		OPTIONAL,
	...
}

InformationExchangeInitiationRequest-IEs RNSAP-PROTOCOL-IES ::= {
	{ ID	id-InformationExchangeID						CRITICALITY	reject		TYPE	InformationExchangeID					PRESENCE	mandatory	}|
	{ ID	id-InformationExchangeObjectType-InfEx-Rqst		CRITICALITY	reject		TYPE 	InformationExchangeObjectType-InfEx-Rqst		PRESENCE 	mandatory	}|

	{ ID	id-InformationType								CRITICALITY	reject		TYPE	InformationType							PRESENCE	mandatory	}|
	{ ID	id-InformationReportCharacteristics				CRITICALITY	reject		TYPE	InformationReportCharacteristics		PRESENCE	mandatory	},
	...
}

InformationExchangeInitiationRequest-Extensions RNSAP-PROTOCOL-EXTENSION ::= {
	...
}

InformationExchangeObjectType-InfEx-Rqst ::= CHOICE {
	cell													Cell-InfEx-Rqst,
	...,
	extension-InformationExchangeObjectType-InfEx-Rqst		Extension-InformationExchangeObjectType-InfEx-Rqst

}

Cell-InfEx-Rqst ::= SEQUENCE {
	c-ID							C-ID, --May be a GERAN cell identifier
	iE-Extensions					ProtocolExtensionContainer  { { CellItem-InfEx-Rqst-ExtIEs} }		OPTIONAL,
	...
}

CellItem-InfEx-Rqst-ExtIEs RNSAP-PROTOCOL-EXTENSION ::= {
	...
}

Extension-InformationExchangeObjectType-InfEx-Rqst	::= ProtocolIE-Single-Container {{ Extension-InformationExchangeObjectType-InfEx-RqstIE }}

Extension-InformationExchangeObjectType-InfEx-RqstIE RNSAP-PROTOCOL-IES ::= {
	{ ID id-GSM-Cell-InfEx-Rqst								CRITICALITY reject			TYPE GSM-Cell-InfEx-Rqst												PRESENCE mandatory }|
	{ ID id-MBMS-Bearer-Service-List						CRITICALITY		reject		TYPE	MBMS-Bearer-Service-List									PRESENCE	mandatory}|
	{ ID id-MBMS-Bearer-Service-in-MBMS-Cell-InfEx-Rqst		CRITICALITY		reject		TYPE	MBMS-Bearer-Service-in-MBMS-Cell-InfEx-Rqst			PRESENCE	mandatory}|
	{ ID id-MBMS-Cell-InfEx-Rqst							CRITICALITY		reject		TYPE	MBMS-Cell-InfEx-Rqst							PRESENCE	mandatory}

}

GSM-Cell-InfEx-Rqst ::= SEQUENCE {
	cGI								CGI,
	iE-Extensions					ProtocolExtensionContainer  { { GSMCellItem-InfEx-Rqst-ExtIEs} }		OPTIONAL,
	...
}

GSMCellItem-InfEx-Rqst-ExtIEs RNSAP-PROTOCOL-EXTENSION ::= {
	...
}


MBMS-Bearer-Service-in-MBMS-Cell-InfEx-Rqst	::= SEQUENCE (SIZE (1..maxNrOfCells)) OF MBMS-Bearer-Service-in-MBMS-Cell-Item-InfEx-Rqst

MBMS-Bearer-Service-in-MBMS-Cell-Item-InfEx-Rqst	::= SEQUENCE {
	c-ID							C-ID,
	mBMS-Bearer-Service-List-InfEx-Rqst							MBMS-Bearer-Service-List-InfEx-Rqst,
	iE-Extensions					ProtocolExtensionContainer  { { MBMS-Bearer-Service-in-MBMS-Cell-Item-InfEx-Rqst-ExtIEs} }		OPTIONAL,
	...
}

MBMS-Bearer-Service-in-MBMS-Cell-Item-InfEx-Rqst-ExtIEs RNSAP-PROTOCOL-EXTENSION ::= {
	...
}

MBMS-Bearer-Service-List-InfEx-Rqst	::=	SEQUENCE (SIZE (1..maxNrOfMBMSServices)) OF TMGI

MBMS-Cell-InfEx-Rqst	::= SEQUENCE (SIZE (1..maxNrOfCells)) OF C-ID


-- **************************************************************
--
-- INFORMATION EXCHANGE INITIATION RESPONSE
--
-- **************************************************************

InformationExchangeInitiationResponse ::= SEQUENCE {
	protocolIEs				ProtocolIE-Container	{{InformationExchangeInitiationResponse-IEs}},
	protocolExtensions		ProtocolExtensionContainer	{{InformationExchangeInitiationResponse-Extensions}}		OPTIONAL,
	...
}

InformationExchangeInitiationResponse-IEs RNSAP-PROTOCOL-IES ::= {
	{ ID	id-InformationExchangeID					CRITICALITY ignore	TYPE	InformationExchangeID					PRESENCE	mandatory	}|
	{ ID	id-InformationExchangeObjectType-InfEx-Rsp	CRITICALITY ignore	TYPE	InformationExchangeObjectType-InfEx-Rsp		PRESENCE	optional	}|
	{ ID	id-CriticalityDiagnostics					CRITICALITY ignore	TYPE	CriticalityDiagnostics					PRESENCE	optional	},
	...
}

InformationExchangeInitiationResponse-Extensions RNSAP-PROTOCOL-EXTENSION ::= {
	...
}

InformationExchangeObjectType-InfEx-Rsp ::= CHOICE {
	cell						Cell-InfEx-Rsp,
	...,
	extension-InformationExchangeObjectType-InfEx-Rsp		Extension-InformationExchangeObjectType-InfEx-Rsp
}

Cell-InfEx-Rsp ::= SEQUENCE {
	requestedDataValue				RequestedDataValue,
	iE-Extensions					ProtocolExtensionContainer  { { CellItem-InfEx-Rsp-ExtIEs} }		OPTIONAL,
	...
}

CellItem-InfEx-Rsp-ExtIEs RNSAP-PROTOCOL-EXTENSION ::= {
	...
}


Extension-InformationExchangeObjectType-InfEx-Rsp	::= ProtocolIE-Single-Container {{ Extension-InformationExchangeObjectType-InfEx-RspIE }}

Extension-InformationExchangeObjectType-InfEx-RspIE RNSAP-PROTOCOL-IES ::= {
	{ ID id-MBMS-Bearer-Service-List-InfEx-Rsp				CRITICALITY		ignore		TYPE	MBMS-Bearer-Service-List-InfEx-Rsp						PRESENCE	mandatory}|
	{ ID id-MBMS-Bearer-Service-in-MBMS-Cell-InfEx-Rsp		CRITICALITY		ignore		TYPE	MBMS-Bearer-Service-in-MBMS-Cell-InfEx-Rsp				PRESENCE	mandatory}|
	{ ID id-MBMS-Cell-InfEx-Rsp								CRITICALITY		ignore		TYPE	MBMS-Cell-InfEx-Rsp											PRESENCE	mandatory}

}

MBMS-Bearer-Service-List-InfEx-Rsp	::= SEQUENCE (SIZE (1..maxNrOfMBMSServices)) OF MBMS-Bearer-ServiceItemIEs-InfEx-Rsp



MBMS-Bearer-ServiceItemIEs-InfEx-Rsp	::=SEQUENCE{
	tmgi	TMGI,
	requestedDataValue		RequestedDataValue,
	iE-Extensions					ProtocolExtensionContainer { { MBMS-Bearer-ServiceItem-InfEx-Rsp-ExtIEs} } OPTIONAL,
	...
}

MBMS-Bearer-ServiceItem-InfEx-Rsp-ExtIEs	RNSAP-PROTOCOL-EXTENSION ::= {
	...
}

MBMS-Bearer-Service-in-MBMS-Cell-InfEx-Rsp	::= SEQUENCE (SIZE (1..maxNrOfCells)) OF MBMS-Bearer-Service-in-MBMS-Cell-Item-InfEx-Rsp

MBMS-Bearer-Service-in-MBMS-Cell-Item-InfEx-Rsp	::= SEQUENCE {
	c-ID							C-ID,
	mBMS-Bearer-Service-List-InfEx-Rsp							MBMS-Bearer-Service-List-InfEx-Rsp,
	iE-Extensions					ProtocolExtensionContainer  { { MBMS-Bearer-Service-in-MBMS-Cell-Item-InfEx-Rsp-ExtIEs} }		OPTIONAL,
	...
}

MBMS-Bearer-Service-in-MBMS-Cell-Item-InfEx-Rsp-ExtIEs RNSAP-PROTOCOL-EXTENSION ::= {
	...
}

MBMS-Cell-InfEx-Rsp	::= SEQUENCE (SIZE (1..maxNrOfCells)) OF MBMS-Cell-Item-InfEx-Rsp

MBMS-Cell-Item-InfEx-Rsp	::= SEQUENCE {
	c-ID							C-ID,
	requestedDataValue				RequestedDataValue,
	iE-Extensions					ProtocolExtensionContainer  { { MBMS-Cell-Item-InfEx-Rsp-ExtIEs} }		OPTIONAL,
	...
}

MBMS-Cell-Item-InfEx-Rsp-ExtIEs RNSAP-PROTOCOL-EXTENSION ::= {
	...
}

-- **************************************************************
--
-- INFORMATION EXCHANGE INITIATION FAILURE
--
-- **************************************************************

InformationExchangeInitiationFailure ::= SEQUENCE {
	protocolIEs				ProtocolIE-Container	{{InformationExchangeInitiationFailure-IEs}},
	protocolExtensions		ProtocolExtensionContainer	{{InformationExchangeInitiationFailure-Extensions}}		OPTIONAL,
	...
}

InformationExchangeInitiationFailure-IEs RNSAP-PROTOCOL-IES ::= {
	{ ID	id-InformationExchangeID				CRITICALITY		ignore			TYPE	InformationExchangeID				PRESENCE	mandatory	}|
	{ ID	id-Cause								CRITICALITY		ignore			TYPE	Cause										PRESENCE	mandatory	}|
	{ ID	id-CriticalityDiagnostics				CRITICALITY		ignore			TYPE	CriticalityDiagnostics				PRESENCE	optional	},
	...
}

InformationExchangeInitiationFailure-Extensions RNSAP-PROTOCOL-EXTENSION ::= {
	...
}

-- **************************************************************
--
-- INFORMATION REPORT
--
-- **************************************************************

InformationReport ::= SEQUENCE {
	protocolIEs				ProtocolIE-Container	{{InformationReport-IEs}},
	protocolExtensions		ProtocolExtensionContainer	{{InformationReport-Extensions}}		OPTIONAL,
	...
}

InformationReport-IEs RNSAP-PROTOCOL-IES ::= {
	{ ID	id-InformationExchangeID						CRITICALITY	ignore			TYPE	InformationExchangeID								PRESENCE	mandatory	}|
	{ ID	id-InformationExchangeObjectType-InfEx-Rprt		CRITICALITY	ignore			TYPE	InformationExchangeObjectType-InfEx-Rprt		PRESENCE	mandatory	},
	...
}

InformationReport-Extensions RNSAP-PROTOCOL-EXTENSION ::= {
	...
}

InformationExchangeObjectType-InfEx-Rprt ::= CHOICE {
	cell							Cell-InfEx-Rprt,
	...,
	extension-InformationExchangeObjectType-InfEx-Rprt		Extension-InformationExchangeObjectType-InfEx-Rprt

 }

Extension-InformationExchangeObjectType-InfEx-Rprt	::= ProtocolIE-Single-Container {{ Extension-InformationExchangeObjectType-InfEx-RprtIE }}

Extension-InformationExchangeObjectType-InfEx-RprtIE RNSAP-PROTOCOL-IES ::= {
	{ ID id-MBMS-Bearer-Service-in-MBMS-Cell-InfEx-Rprt		CRITICALITY		ignore		TYPE	MBMS-Bearer-Service-in-MBMS-Cell-InfEx-Rprt			PRESENCE	mandatory}|
	{ ID id-MBMS-Cell-InfEx-Rprt							CRITICALITY		ignore		TYPE	MBMS-Cell-InfEx-Rprt										PRESENCE	mandatory}

}


Cell-InfEx-Rprt ::= SEQUENCE {
	requestedDataValueInformation	RequestedDataValueInformation,
	iE-Extensions					ProtocolExtensionContainer  {{ CellItem-InfEx-Rprt-ExtIEs }}		OPTIONAL,
	...

 }

CellItem-InfEx-Rprt-ExtIEs RNSAP-PROTOCOL-EXTENSION ::= {
	...
}


MBMS-Bearer-Service-in-MBMS-Cell-InfEx-Rprt	::= SEQUENCE (SIZE (1..maxNrOfCells)) OF MBMS-Bearer-Service-in-MBMS-Cell-Item-InfEx-Rprt

MBMS-Bearer-Service-in-MBMS-Cell-Item-InfEx-Rprt	::= SEQUENCE {
	c-ID							C-ID,
	mBMS-Bearer-Service-List-InfEx-Rprt							MBMS-Bearer-Service-List-InfEx-Rprt,
	iE-Extensions					ProtocolExtensionContainer  { { MBMS-Bearer-Service-in-MBMS-Cell-Item-InfEx-Rprt-ExtIEs} }		OPTIONAL,
	...
}

MBMS-Bearer-Service-in-MBMS-Cell-Item-InfEx-Rprt-ExtIEs RNSAP-PROTOCOL-EXTENSION ::= {
	...
}

MBMS-Bearer-Service-List-InfEx-Rprt	::= SEQUENCE (SIZE (1..maxNrOfMBMSServices)) OF MBMS-Bearer-Service-List-Item-InfEx-Rprt

MBMS-Bearer-Service-List-Item-InfEx-Rprt	::=	SEQUENCE {
	tmgi					TMGI,
	requestedDataValueInformation	RequestedDataValueInformation,
	iE-Extensions					ProtocolExtensionContainer  { { MBMS-Bearer-Service-List-Item-InfEx-Rprt-ExtIEs} }		OPTIONAL,
	...
}

MBMS-Bearer-Service-List-Item-InfEx-Rprt-ExtIEs RNSAP-PROTOCOL-EXTENSION ::= {
	...
}

MBMS-Cell-InfEx-Rprt	::= SEQUENCE (SIZE (1..maxNrOfCells)) OF MBMS-Cell-Item-InfEx-Rprt

MBMS-Cell-Item-InfEx-Rprt	::= SEQUENCE {
	c-ID							C-ID,
	requestedDataValueInformation	RequestedDataValueInformation,
	iE-Extensions					ProtocolExtensionContainer  { { MBMS-Cell-Item-InfEx-Rprt-ExtIEs} }		OPTIONAL,
	...
}

MBMS-Cell-Item-InfEx-Rprt-ExtIEs RNSAP-PROTOCOL-EXTENSION ::= {
	...
}

-- **************************************************************
--
-- INFORMATION EXCHANGE TERMINATION REQUEST
--
-- **************************************************************

InformationExchangeTerminationRequest ::= SEQUENCE {
	protocolIEs				ProtocolIE-Container	{{InformationExchangeTerminationRequest-IEs}},
	protocolExtensions		ProtocolExtensionContainer	{{InformationExchangeTerminationRequest-Extensions}}		OPTIONAL,
	...
}

InformationExchangeTerminationRequest-IEs RNSAP-PROTOCOL-IES ::= {
	{ ID	id-InformationExchangeID			CRITICALITY		ignore				TYPE	InformationExchangeID			PRESENCE	mandatory},
	...
}

InformationExchangeTerminationRequest-Extensions RNSAP-PROTOCOL-EXTENSION ::= {
	...
}


-- **************************************************************
--
-- INFORMATION EXCHANGE FAILURE INDICATION
--
-- **************************************************************

InformationExchangeFailureIndication ::= SEQUENCE {
	protocolIEs				ProtocolIE-Container	{{InformationExchangeFailureIndication-IEs}},
	protocolExtensions			ProtocolExtensionContainer	{{InformationExchangeFailureIndication-Extensions}}				OPTIONAL,
	...
}

InformationExchangeFailureIndication-IEs RNSAP-PROTOCOL-IES ::= {
	{ ID	id-InformationExchangeID			CRITICALITY	ignore			TYPE	InformationExchangeID			PRESENCE	mandatory	}|
	{ ID	id-Cause							CRITICALITY	ignore			TYPE	Cause								PRESENCE	mandatory	},
	...
}

InformationExchangeFailureIndication-Extensions RNSAP-PROTOCOL-EXTENSION ::= {
	...
}

-- **************************************************************
--
-- RESET REQUEST
--
-- **************************************************************

ResetRequest ::= SEQUENCE {
	protocolIEs				ProtocolIE-Container	{{ResetRequest-IEs}},
	protocolExtensions		ProtocolExtensionContainer	{{ResetRequest-Extensions}}		OPTIONAL,
	...
}

ResetRequest-IEs RNSAP-PROTOCOL-IES ::= {
	{ ID id-RNC-ID				CRITICALITY reject	TYPE RNC-ID		PRESENCE mandatory} |
	{ ID id-ResetIndicator		CRITICALITY	reject		TYPE 	ResetIndicator		PRESENCE 	mandatory},
	...
}

ResetRequest-Extensions RNSAP-PROTOCOL-EXTENSION ::= {
	{ ID id-Extended-RNC-ID				CRITICALITY reject	EXTENSION Extended-RNC-ID		PRESENCE optional},
	...
}

ResetIndicator ::= CHOICE {
	context			ContextList-Reset,
	all-contexts		NULL,
	...,
	contextGroup	ContextGroupList-Reset
}

ContextList-Reset ::= SEQUENCE {
	contextInfoList-Reset		ContextInfoList-Reset,
	iE-Extensions							ProtocolExtensionContainer  { {ContextItem-Reset-ExtIEs} }		OPTIONAL,
	...
}

ContextItem-Reset-ExtIEs RNSAP-PROTOCOL-EXTENSION ::= {
	...
}

ContextInfoList-Reset ::= SEQUENCE (SIZE (1.. maxResetContext))	OF ProtocolIE-Single-Container {{ ContextInfoItemIE-Reset }}

ContextInfoItemIE-Reset RNSAP-PROTOCOL-IES ::= {
	{ID id-ContextInfoItem-Reset		CRITICALITY reject		TYPE ContextInfoItem-Reset		PRESENCE mandatory}
}

ContextInfoItem-Reset ::= SEQUENCE {
	contextType-Reset			ContextType-Reset,
	iE-Extensions				ProtocolExtensionContainer  { { ContextInfoItem-Reset-ExtIEs} }		OPTIONAL,
	...
}

ContextInfoItem-Reset-ExtIEs RNSAP-PROTOCOL-EXTENSION ::= {
	...
}

ContextType-Reset ::= CHOICE {
	sRNTI			S-RNTI,
	dRNTI			D-RNTI,
	...
}

ContextGroupList-Reset ::= SEQUENCE {
	contextGroupInfoList-Reset		ContextGroupInfoList-Reset,
	iE-Extensions					ProtocolExtensionContainer  { {ContextGroupItem-Reset-ExtIEs} }		OPTIONAL,
	...
}

ContextGroupItem-Reset-ExtIEs RNSAP-PROTOCOL-EXTENSION ::= {
	...
}

ContextGroupInfoList-Reset ::= SEQUENCE (SIZE (1.. maxResetContextGroup))	OF ProtocolIE-Single-Container {{ ContextGroupInfoItemIE-Reset }}

ContextGroupInfoItemIE-Reset RNSAP-PROTOCOL-IES ::= {
	{ID id-ContextGroupInfoItem-Reset		CRITICALITY reject		TYPE ContextGroupInfoItem-Reset		PRESENCE mandatory}
}

ContextGroupInfoItem-Reset ::= SEQUENCE {
	s-RNTI-Group				S-RNTI-Group,
	iE-Extensions				ProtocolExtensionContainer  { { ContextGroupInfoItem-Reset-ExtIEs} }		OPTIONAL,
	...
}

ContextGroupInfoItem-Reset-ExtIEs RNSAP-PROTOCOL-EXTENSION ::= {
	...
}

-- **************************************************************
--
-- RESET RESPONSE
--
-- **************************************************************

ResetResponse ::= SEQUENCE {
	protocolIEs				ProtocolIE-Container	{{ResetResponse-IEs}},
	protocolExtensions		ProtocolExtensionContainer	{{ResetResponse-Extensions}}     		OPTIONAL,
	...
}

ResetResponse-IEs RNSAP-PROTOCOL-IES ::= {
	{ ID id-RNC-ID				CRITICALITY ignore	TYPE RNC-ID		PRESENCE mandatory} |
	{ ID id-CriticalityDiagnostics		CRITICALITY		ignore		TYPE	CriticalityDiagnostics		PRESENCE	optional},
	...
}

ResetResponse-Extensions RNSAP-PROTOCOL-EXTENSION ::= {
	{ ID id-Extended-RNC-ID				CRITICALITY reject	EXTENSION Extended-RNC-ID		PRESENCE optional},
	...
}

-- **************************************************************
--
-- RADIO LINK ACTIVATION COMMAND FDD
--
-- **************************************************************

RadioLinkActivationCommandFDD ::= SEQUENCE {
	protocolIEs				ProtocolIE-Container	{{RadioLinkActivationCommandFDD-IEs}},
	protocolExtensions		ProtocolExtensionContainer	{{RadioLinkActivationCommandFDD-Extensions}}			OPTIONAL,
	...
}

RadioLinkActivationCommandFDD-IEs RNSAP-PROTOCOL-IES ::= {
	{ ID id-DelayedActivationList-RL-ActivationCmdFDD		CRITICALITY	ignore	TYPE	DelayedActivationInformationList-RL-ActivationCmdFDD			PRESENCE	mandatory	},
	...
}

RadioLinkActivationCommandFDD-Extensions RNSAP-PROTOCOL-EXTENSION ::= {
	...
}

DelayedActivationInformationList-RL-ActivationCmdFDD ::= SEQUENCE (SIZE (1..maxNrOfRLs)) OF ProtocolIE-Single-Container {
	{ DelayedActivationInformation-RL-ActivationCmdFDD-IEs} }

DelayedActivationInformation-RL-ActivationCmdFDD-IEs RNSAP-PROTOCOL-IES ::= {
	{ ID id-DelayedActivationInformation-RL-ActivationCmdFDD	CRITICALITY ignore	TYPE DelayedActivationInformation-RL-ActivationCmdFDD	PRESENCE optional	}
}

DelayedActivationInformation-RL-ActivationCmdFDD ::= SEQUENCE {
	rL-ID						RL-ID,
	delayed-activation-update	DelayedActivationUpdate,
	iE-Extensions				ProtocolExtensionContainer { { DelayedActivationInformation-RL-ActivationCmdFDD-ExtIEs} } OPTIONAL,
	...
}

DelayedActivationInformation-RL-ActivationCmdFDD-ExtIEs RNSAP-PROTOCOL-EXTENSION ::= {
	...
}

-- **************************************************************
--
-- RADIO LINK ACTIVATION COMMAND TDD
--
-- **************************************************************

RadioLinkActivationCommandTDD ::= SEQUENCE {
	protocolIEs				ProtocolIE-Container	{{RadioLinkActivationCommandTDD-IEs}},
	protocolExtensions		ProtocolExtensionContainer	{{RadioLinkActivationCommandTDD-Extensions}}			OPTIONAL,
	...
}

RadioLinkActivationCommandTDD-IEs RNSAP-PROTOCOL-IES ::= {
	{ ID id-DelayedActivationList-RL-ActivationCmdTDD		CRITICALITY	ignore	TYPE	DelayedActivationInformationList-RL-ActivationCmdTDD			PRESENCE	mandatory	},
	...
}

RadioLinkActivationCommandTDD-Extensions RNSAP-PROTOCOL-EXTENSION ::= {
	...
}

DelayedActivationInformationList-RL-ActivationCmdTDD ::= SEQUENCE (SIZE (1..maxNrOfRLs)) OF ProtocolIE-Single-Container {
	{ DelayedActivationInformation-RL-ActivationCmdTDD-IEs} }

DelayedActivationInformation-RL-ActivationCmdTDD-IEs RNSAP-PROTOCOL-IES ::= {
	{ ID id-DelayedActivationInformation-RL-ActivationCmdTDD	CRITICALITY ignore	TYPE DelayedActivationInformation-RL-ActivationCmdTDD	PRESENCE optional	}
}

DelayedActivationInformation-RL-ActivationCmdTDD ::= SEQUENCE {
	rL-ID						RL-ID,
	delayed-activation-update	DelayedActivationUpdate,
	iE-Extensions				ProtocolExtensionContainer { { DelayedActivationInformation-RL-ActivationCmdTDD-ExtIEs} } OPTIONAL,
	...
}

DelayedActivationInformation-RL-ActivationCmdTDD-ExtIEs RNSAP-PROTOCOL-EXTENSION ::= {
	...
}

-- **************************************************************
--
-- GERAN UPLINK SIGNALLING TRANSFER INDICATION
--
-- **************************************************************

GERANUplinkSignallingTransferIndication ::= SEQUENCE {
	protocolIEs                     ProtocolIE-Container       {{GERANUplinkSignallingTransferIndication-IEs}},
	protocolExtensions              ProtocolExtensionContainer {{GERANUplinkSignallingTransferIndication-Extensions}}	OPTIONAL,
	...
}

GERANUplinkSignallingTransferIndication-IEs RNSAP-PROTOCOL-IES ::= {
	{ ID id-UC-ID						CRITICALITY ignore	TYPE UC-ID							PRESENCE mandatory	}	|
	-- UC-Id may be GERAN cell identifier.
	{ ID id-SAI							CRITICALITY ignore	TYPE SAI							PRESENCE mandatory	}	|
	{ ID id-S-RNTI						CRITICALITY ignore	TYPE S-RNTI							PRESENCE mandatory	}	|
	{ ID id-D-RNTI						CRITICALITY ignore	TYPE D-RNTI							PRESENCE optional	}	|
	{ ID id-L3-Information				CRITICALITY ignore	TYPE L3-Information					PRESENCE mandatory	}	|
	{ ID id-CN-PS-DomainIdentifier		CRITICALITY ignore	TYPE CN-PS-DomainIdentifier			PRESENCE optional	} 	|
	{ ID id-CN-CS-DomainIdentifier		CRITICALITY ignore	TYPE CN-CS-DomainIdentifier			PRESENCE optional	} 	|
	{ ID id-URA-Information				CRITICALITY ignore	TYPE URA-Information				PRESENCE optional	},
	-- URA information may be GRA information
	...
}

GERANUplinkSignallingTransferIndication-Extensions RNSAP-PROTOCOL-EXTENSION ::= {
	...
}

-- **************************************************************
--
-- RADIO LINK PARAMETER UPDATE INDICATION FDD
--
-- **************************************************************

RadioLinkParameterUpdateIndicationFDD ::= SEQUENCE {
	protocolIEs				ProtocolIE-Container	{{RadioLinkParameterUpdateIndicationFDD-IEs}},
	protocolExtensions		ProtocolExtensionContainer	{{RadioLinkParameterUpdateIndicationFDD-Extensions}}		OPTIONAL,
	...
}

RadioLinkParameterUpdateIndicationFDD-IEs RNSAP-PROTOCOL-IES ::= {
	{ ID	id-HSDSCH-FDD-Update-Information						CRITICALITY ignore	TYPE	HSDSCH-FDD-Update-Information			PRESENCE	optional}|
	{ ID	id-RL-ParameterUpdateIndicationFDD-RL-InformationList	CRITICALITY ignore	TYPE	RL-ParameterUpdateIndicationFDD-RL-InformationList		PRESENCE optional	},
	...
}

RL-ParameterUpdateIndicationFDD-RL-InformationList ::= SEQUENCE (SIZE (1..maxNrOfRLs)) OF ProtocolIE-Single-Container { { RL-ParameterUpdateIndicationFDD-RL-InformationList-IEs} }

RL-ParameterUpdateIndicationFDD-RL-InformationList-IEs RNSAP-PROTOCOL-IES ::= {
	{ ID id-RL-ParameterUpdateIndicationFDD-RL-Information-Item		CRITICALITY ignore	TYPE RL-ParameterUpdateIndicationFDD-RL-Information-Item		PRESENCE mandatory	}
}

RL-ParameterUpdateIndicationFDD-RL-Information-Item::= SEQUENCE {
	rL-ID								RL-ID,
	phase-Reference-Update-Indicator	Phase-Reference-Update-Indicator	OPTIONAL,
	iE-Extensions						ProtocolExtensionContainer { { RL-ParameterUpdateIndicationFDD-RL-Information-ExtIEs} } OPTIONAL,
	...
}

RL-ParameterUpdateIndicationFDD-RL-Information-ExtIEs RNSAP-PROTOCOL-EXTENSION ::= {
	...
}

RadioLinkParameterUpdateIndicationFDD-Extensions RNSAP-PROTOCOL-EXTENSION ::= {
	{ ID id-E-DCH-FDD-Update-Information	CRITICALITY ignore		EXTENSION E-DCH-FDD-Update-Information	PRESENCE optional	}|
	{ ID id-Additional-HS-Cell-Information-RL-Param-Upd	CRITICALITY ignore		EXTENSION Additional-HS-Cell-Information-RL-Param-Upd		PRESENCE optional }|
	{ ID id-Additional-EDCH-Cell-Information-RL-Param-Upd	CRITICALITY ignore		EXTENSION Additional-EDCH-Cell-Information-RL-Param-Upd		PRESENCE optional },
	...
}

Additional-HS-Cell-Information-RL-Param-Upd	::= SEQUENCE (SIZE (1..maxNrOfHSDSCH-1)) OF Additional-HS-Cell-Information-RL-Param-Upd-ItemIEs



Additional-HS-Cell-Information-RL-Param-Upd-ItemIEs	::=SEQUENCE{
	hSPDSCH-RL-ID										RL-ID,
	hS-DSCH-FDD-Secondary-Serving-Update-Information	HS-DSCH-FDD-Secondary-Serving-Update-Information,
	iE-Extensions					ProtocolExtensionContainer { { Additional-HS-Cell-Information-RL-Setup-ExtIEs} } OPTIONAL,
	...
}

Additional-HS-Cell-Information-RL-Setup-ExtIEs	RNSAP-PROTOCOL-EXTENSION ::= {
	...
}

Additional-EDCH-Cell-Information-RL-Param-Upd	::= SEQUENCE (SIZE (1..maxNrOfEDCH-1)) OF Additional-EDCH-Cell-Information-RL-Param-Upd-ItemIEs

Additional-EDCH-Cell-Information-RL-Param-Upd-ItemIEs	::=SEQUENCE{
	additional-EDCH-FDD-Update-Information										Additional-EDCH-FDD-Update-Information,
	iE-Extensions					ProtocolExtensionContainer { { Additional-EDCH-FDD-Update-Information-ExtIEs} } OPTIONAL,
	...
}

Additional-EDCH-FDD-Update-Information-ExtIEs	RNSAP-PROTOCOL-EXTENSION ::= {
	...
}

-- **************************************************************
--
-- RADIO LINK PARAMETER UPDATE INDICATION TDD
--
-- **************************************************************

RadioLinkParameterUpdateIndicationTDD ::= SEQUENCE {
	protocolIEs				ProtocolIE-Container	{{RadioLinkParameterUpdateIndicationTDD-IEs}},
	protocolExtensions		ProtocolExtensionContainer	{{RadioLinkParameterUpdateIndicationTDD-Extensions}}		OPTIONAL,
	...
}

RadioLinkParameterUpdateIndicationTDD-IEs RNSAP-PROTOCOL-IES ::= {
	{ ID	id-HSDSCH-TDD-Update-Information		CRITICALITY		ignore		TYPE	HSDSCH-TDD-Update-Information			PRESENCE	optional},
	...
}

RadioLinkParameterUpdateIndicationTDD-Extensions RNSAP-PROTOCOL-EXTENSION ::= {
	...
}

-- **************************************************************
--
-- UE MEASUREMENT INITIATION REQUEST
--
-- **************************************************************

UEMeasurementInitiationRequest ::= SEQUENCE {
	protocolIEs                     ProtocolIE-Container       {{UEMeasurementInitiationRequest-IEs}},
	protocolExtensions              ProtocolExtensionContainer {{UEMeasurementInitiationRequest-Extensions}}                   OPTIONAL,
	...
}

UEMeasurementInitiationRequest-IEs RNSAP-PROTOCOL-IES ::= {
	{ ID id-AllowedQueuingTime					CRITICALITY reject	TYPE AllowedQueuingTime 						PRESENCE optional		} |
	{ ID id-MeasurementID						CRITICALITY reject	TYPE MeasurementID								PRESENCE mandatory	} |
	{ ID id-UEMeasurementType					CRITICALITY reject	TYPE UEMeasurementType							PRESENCE mandatory	} |
	{ ID id-UEMeasurementTimeslotInfoHCR		CRITICALITY reject	TYPE UEMeasurementTimeslotInfoHCR			PRESENCE optional		} |
	{ ID id-UEMeasurementTimeslotInfoLCR		CRITICALITY reject	TYPE UEMeasurementTimeslotInfoLCR			PRESENCE optional		} |
	{ ID id-MeasurementFilterCoefficient		CRITICALITY reject	TYPE MeasurementFilterCoefficient			PRESENCE optional		} |
	{ ID id-UEMeasurementReportCharacteristics	CRITICALITY reject	TYPE UEMeasurementReportCharacteristics	PRESENCE mandatory	} |
	{ ID id-UEMeasurementParameterModAllow		CRITICALITY reject  TYPE UEMeasurementParameterModAllow			PRESENCE mandatory	},
	...
}

UEMeasurementInitiationRequest-Extensions RNSAP-PROTOCOL-EXTENSION ::= {
	{ ID id-UEMeasurementTimeslotInfo768				CRITICALITY reject	EXTENSION UEMeasurementTimeslotInfo768	PRESENCE optional},
	...
}

-- **************************************************************
--
-- UE MEASUREMENT INITIATION RESPONSE
--
-- **************************************************************

UEMeasurementInitiationResponse ::= SEQUENCE {
	protocolIEs                     ProtocolIE-Container       {{UEMeasurementInitiationResponse-IEs}},
	protocolExtensions              ProtocolExtensionContainer {{UEMeasurementInitiationResponse-Extensions}}                   OPTIONAL,
	...
}

UEMeasurementInitiationResponse-IEs RNSAP-PROTOCOL-IES ::= {
	{ ID id-MeasurementID						CRITICALITY ignore	TYPE MeasurementID								PRESENCE mandatory	} |
	{ ID id-MeasurementFilterCoefficient		CRITICALITY reject	TYPE MeasurementFilterCoefficient			PRESENCE optional		} |
	{ ID id-UEMeasurementReportCharacteristics	CRITICALITY reject	TYPE UEMeasurementReportCharacteristics	PRESENCE optional		} |
	{ ID id-CriticalityDiagnostics				CRITICALITY ignore	TYPE CriticalityDiagnostics						PRESENCE optional	},
	...
}

UEMeasurementInitiationResponse-Extensions RNSAP-PROTOCOL-EXTENSION ::= {
	...
}

-- **************************************************************
--
-- UE MEASUREMENT INITIATION FAILURE
--
-- **************************************************************

UEMeasurementInitiationFailure ::= SEQUENCE {
	protocolIEs                     ProtocolIE-Container       {{UEMeasurementInitiationFailure-IEs}},
	protocolExtensions              ProtocolExtensionContainer {{UEMeasurementInitiationFailure-Extensions}}                   OPTIONAL,
	...
}

UEMeasurementInitiationFailure-IEs RNSAP-PROTOCOL-IES ::= {
	{ ID id-MeasurementID					CRITICALITY ignore	TYPE MeasurementID						PRESENCE mandatory	} |
	{ ID id-Cause							CRITICALITY ignore	TYPE Cause								PRESENCE mandatory	} |
	{ ID id-CriticalityDiagnostics			CRITICALITY ignore	TYPE CriticalityDiagnostics				PRESENCE optional	},
	...
}

UEMeasurementInitiationFailure-Extensions RNSAP-PROTOCOL-EXTENSION ::= {
	...
}

-- **************************************************************
--
-- UE MEASUREMENT REPORT
--
-- **************************************************************

UEMeasurementReport ::= SEQUENCE {
	protocolIEs                     ProtocolIE-Container       {{UEMeasurementReport-IEs}},
	protocolExtensions              ProtocolExtensionContainer {{UEMeasurementReport-Extensions}}                   OPTIONAL,
	...
}

UEMeasurementReport-IEs RNSAP-PROTOCOL-IES ::= {
	{ ID id-MeasurementID					CRITICALITY ignore	TYPE MeasurementID							PRESENCE mandatory	} |
	{ ID id-UEMeasurementValueInformation	CRITICALITY ignore	TYPE UEMeasurementValueInformation		PRESENCE mandatory	},
	...
}

UEMeasurementReport-Extensions RNSAP-PROTOCOL-EXTENSION ::= {
	...
}

-- **************************************************************
--
-- UE MEASUREMENT TERMINATION REQUEST
--
-- **************************************************************

UEMeasurementTerminationRequest ::= SEQUENCE {
	protocolIEs                     ProtocolIE-Container       {{UEMeasurementTerminationRequest-IEs}},
	protocolExtensions              ProtocolExtensionContainer {{UEMeasurementTerminationRequest-Extensions}}                   OPTIONAL,
	...
}

UEMeasurementTerminationRequest-IEs RNSAP-PROTOCOL-IES ::= {
	{ ID id-MeasurementID				CRITICALITY ignore	TYPE MeasurementID				PRESENCE mandatory	},
	...
}

UEMeasurementTerminationRequest-Extensions RNSAP-PROTOCOL-EXTENSION ::= {
	...
}

-- **************************************************************
--
-- UE MEASUREMENT FAILURE INDICATION
--
-- **************************************************************

UEMeasurementFailureIndication ::= SEQUENCE {
	protocolIEs                     ProtocolIE-Container       {{UEMeasurementFailureIndication-IEs}},
	protocolExtensions              ProtocolExtensionContainer {{UEMeasurementFailureIndication-Extensions}}                   OPTIONAL,
	...
}

UEMeasurementFailureIndication-IEs RNSAP-PROTOCOL-IES ::= {
	{ ID id-MeasurementID				CRITICALITY ignore	TYPE MeasurementID				PRESENCE mandatory	} |
	{ ID id-Cause						CRITICALITY ignore	TYPE Cause						PRESENCE mandatory	},
	...
}

UEMeasurementFailureIndication-Extensions RNSAP-PROTOCOL-EXTENSION ::= {
	...
}

-- **************************************************************
--
-- IUR INVOKE TRACE
--
-- **************************************************************

IurInvokeTrace ::= SEQUENCE {
	protocolIEs									ProtocolIE-Container		{{IurInvokeTrace-IEs}},
	protocolExtensions							ProtocolExtensionContainer	{{IurInvokeTrace-Extensions}}		OPTIONAL,
	...
}

IurInvokeTrace-IEs RNSAP-PROTOCOL-IES ::= {
	{ ID id-D-RNTI								CRITICALITY ignore	TYPE D-RNTI										PRESENCE optional		}|
	{ ID id-TraceReference						CRITICALITY ignore	TYPE TraceReference								PRESENCE mandatory	}|
	{ ID id-UEIdentity							CRITICALITY ignore	TYPE UEIdentity									PRESENCE mandatory	}|
	{ ID id-TraceRecordingSessionReference		CRITICALITY ignore	TYPE TraceRecordingSessionReference			PRESENCE mandatory	}|
	{ ID id-ListOfInterfacesToTrace				CRITICALITY ignore	TYPE ListOfInterfacesToTrace					PRESENCE optional		}|
	{ ID id-TraceDepth							CRITICALITY ignore	TYPE TraceDepth									PRESENCE mandatory	},
	...
}

ListOfInterfacesToTrace ::= SEQUENCE (SIZE (1..maxNrOfInterfaces)) OF ProtocolIE-Single-Container {{ InterfacesToBeTracedItemIE }}

InterfacesToBeTracedItemIE RNSAP-PROTOCOL-IES ::= {
	{ ID id-InterfacesToTraceItem				CRITICALITY ignore	TYPE InterfacesToTraceItem						PRESENCE mandatory	}
}

InterfacesToTraceItem ::= SEQUENCE {
	interface				ENUMERATED {iub,iur,...},
	iE-Extensions			ProtocolExtensionContainer { {InterfacesToTraceItem-ExtIEs} }	OPTIONAL,
	...
}

InterfacesToTraceItem-ExtIEs RNSAP-PROTOCOL-EXTENSION ::= {
	...
}


IurInvokeTrace-Extensions RNSAP-PROTOCOL-EXTENSION ::= {
	...
}

-- **************************************************************
--
-- IUR DEACTIVATE TRACE
--
-- **************************************************************

IurDeactivateTrace ::= SEQUENCE {
	protocolIEs									ProtocolIE-Container		{{IurDeactivateTrace-IEs}},
	protocolExtensions							ProtocolExtensionContainer	{{IurDeactivateTrace-Extensions}}	OPTIONAL,
	...
}

IurDeactivateTrace-IEs RNSAP-PROTOCOL-IES ::= {
	{ ID id-D-RNTI								CRITICALITY ignore	TYPE D-RNTI										PRESENCE optional		}|
	{ ID id-TraceReference						CRITICALITY ignore	TYPE TraceReference								PRESENCE mandatory	},
	...
}

IurDeactivateTrace-Extensions RNSAP-PROTOCOL-EXTENSION ::= {
	...
}

-- **************************************************************
--
-- MBMS ATTACH COMMAND
--
-- **************************************************************

MBMSAttachCommand ::= SEQUENCE {
	protocolIEs				ProtocolIE-Container	{{MBMSAttachCommand-IEs}},
	protocolExtensions		ProtocolExtensionContainer	{{MBMSAttachCommand-Extensions}}		OPTIONAL,
	...
}

MBMSAttachCommand-IEs RNSAP-PROTOCOL-IES ::= {
	{ ID id-MBMS-Bearer-Service-List		CRITICALITY		ignore		TYPE MBMS-Bearer-Service-List PRESENCE	mandatory} |
	{ ID id-UE-State						CRITICALITY		ignore		TYPE	UE-State				PRESENCE	optional},
	...
}

MBMSAttachCommand-Extensions RNSAP-PROTOCOL-EXTENSION ::= {
	...
}

-- **************************************************************
--
-- MBMS DETACH COMMAND
--
-- **************************************************************

MBMSDetachCommand ::= SEQUENCE {
	protocolIEs				ProtocolIE-Container	{{MBMSDetachCommand-IEs}},
	protocolExtensions		ProtocolExtensionContainer	{{MBMSDetachCommand-Extensions}}		OPTIONAL,
	...
}

MBMSDetachCommand-IEs RNSAP-PROTOCOL-IES ::= {
	{ ID id-MBMS-Bearer-Service-List 	CRITICALITY		ignore		TYPE MBMS-Bearer-Service-List PRESENCE	mandatory} |
	{ ID id-UE-State					CRITICALITY		ignore		TYPE	UE-State				PRESENCE	optional},
	...
}

MBMSDetachCommand-Extensions RNSAP-PROTOCOL-EXTENSION ::= {
	...
}

-- **************************************************************
--
-- DIRECT INFORMATION TRANSFER
--
-- **************************************************************

DirectInformationTransfer ::= SEQUENCE {
	protocolIEs				ProtocolIE-Container		{{DirectInformationTransfer-IEs}},
	protocolExtensions		ProtocolExtensionContainer	{{DirectInformationTransfer-Extensions}}		OPTIONAL,
	...
}

DirectInformationTransfer-IEs RNSAP-PROTOCOL-IES ::= {
	{ ID id-RNC-ID								CRITICALITY ignore 	TYPE RNC-ID									PRESENCE mandatory} |
	{ ID id-ProvidedInformation					CRITICALITY ignore 	TYPE ProvidedInformation					PRESENCE mandatory} ,
	...
}

DirectInformationTransfer-Extensions RNSAP-PROTOCOL-EXTENSION ::= {
	{ ID id-Extended-RNC-ID						CRITICALITY reject	EXTENSION Extended-RNC-ID	PRESENCE optional },
	...
}

-- **************************************************************
--
-- ENHANCED RELOCATION REQUEST
--
-- **************************************************************

EnhancedRelocationRequest ::= SEQUENCE {
	protocolIEs                     ProtocolIE-Container       {{EnhancedRelocationRequest-IEs}},
	protocolExtensions              ProtocolExtensionContainer {{EnhancedRelocationRequest-Extensions}}                   OPTIONAL,
	...
}

EnhancedRelocationRequest-IEs RNSAP-PROTOCOL-IES ::= {
	{ ID id-Cause				CRITICALITY reject	TYPE Cause					PRESENCE mandatory	} |
	{ ID id-Permanent-NAS-UE-Identity	CRITICALITY reject	TYPE Permanent-NAS-UE-Identity	 PRESENCE mandatory } |
	{ ID id-SRNC-ID		CRITICALITY reject	TYPE RNC-ID	PRESENCE optional	}|
	-- This IE shall be present if the Relocation type IE is set to "UE involved in relocation of SRNS" --
	{ ID id-Extended-SRNC-ID	CRITICALITY reject	TYPE Extended-RNC-ID	 PRESENCE optional }|
	{ ID id-S-RNTI		CRITICALITY reject	TYPE S-RNTI	PRESENCE mandatory	}|
	{ ID id-RANAP-EnhancedRelocationInformationRequest		CRITICALITY reject	TYPE RANAP-EnhancedRelocationInformationRequest		PRESENCE mandatory	},
	...
}

EnhancedRelocationRequest-Extensions RNSAP-PROTOCOL-EXTENSION ::= {
	...
}

-- **************************************************************
--
-- ENHANCED RELOCATION RESPONSE
--
-- **************************************************************

EnhancedRelocationResponse ::= SEQUENCE {
	protocolIEs                     ProtocolIE-Container       {{EnhancedRelocationResponse-IEs}},
	protocolExtensions              ProtocolExtensionContainer {{EnhancedRelocationResponse-Extensions}}                   OPTIONAL,
	...
}

EnhancedRelocationResponse-IEs RNSAP-PROTOCOL-IES ::= {
	{ ID id-RANAP-EnhancedRelocationInformationResponse		CRITICALITY ignore	TYPE RANAP-EnhancedRelocationInformationResponse		PRESENCE mandatory	},
	...
}

EnhancedRelocationResponse-Extensions RNSAP-PROTOCOL-EXTENSION ::= {
	...
}

-- **************************************************************
--
-- ENHANCED RELOCATION FAILURE
--
-- **************************************************************

EnhancedRelocationFailure ::= SEQUENCE {
	protocolIEs                     ProtocolIE-Container       {{EnhancedRelocationFailure-IEs}},
	protocolExtensions              ProtocolExtensionContainer {{EnhancedRelocationFailure-Extensions}}                   OPTIONAL,
	...
}

EnhancedRelocationFailure-IEs RNSAP-PROTOCOL-IES ::= {
	{ ID id-Cause		CRITICALITY ignore	TYPE Cause					PRESENCE mandatory	}|
	{ ID id-CriticalityDiagnostics			CRITICALITY ignore	TYPE CriticalityDiagnostics			PRESENCE optional	},
	...
}

EnhancedRelocationFailure-Extensions RNSAP-PROTOCOL-EXTENSION ::= {
	...
}

-- **************************************************************
--
-- ENHANCED RELOCATION CANCEL
--
-- **************************************************************

EnhancedRelocationCancel ::= SEQUENCE {
	protocolIEs                     ProtocolIE-Container       {{EnhancedRelocationCancel-IEs}},
	protocolExtensions              ProtocolExtensionContainer {{EnhancedRelocationCancel-Extensions}}                   OPTIONAL,
	...
}

EnhancedRelocationCancel-IEs RNSAP-PROTOCOL-IES ::= {
	{ ID id-Cause		CRITICALITY ignore	TYPE Cause					PRESENCE mandatory	},
	...
}

EnhancedRelocationCancel-Extensions RNSAP-PROTOCOL-EXTENSION ::= {
	...
}

-- **************************************************************
--
-- ENHANCED RELOCATION SIGNALLING TRANSFER
--
-- **************************************************************

EnhancedRelocationSignallingTransfer ::= SEQUENCE {
	protocolIEs                     ProtocolIE-Container       {{EnhancedRelocationSignallingTransfer-IEs}},
	protocolExtensions              ProtocolExtensionContainer {{EnhancedRelocationSignallingTransfer-Extensions}}                   OPTIONAL,
	...
}

EnhancedRelocationSignallingTransfer-IEs RNSAP-PROTOCOL-IES ::= {
	{ ID id-L3-Information		CRITICALITY ignore	TYPE L3-Information					PRESENCE mandatory	},
	...
}

EnhancedRelocationSignallingTransfer-Extensions RNSAP-PROTOCOL-EXTENSION ::= {
	...
}

-- **************************************************************
--
-- ENHANCED RELOCATION RELEASE
--
-- **************************************************************

EnhancedRelocationRelease ::= SEQUENCE {
	protocolIEs                     ProtocolIE-Container       {{EnhancedRelocationRelease-IEs}},
	protocolExtensions              ProtocolExtensionContainer {{EnhancedRelocationRelease-Extensions}}                   OPTIONAL,
	...
}

EnhancedRelocationRelease-IEs RNSAP-PROTOCOL-IES ::= {
	{ ID id-Released-CN-Domain		CRITICALITY ignore	TYPE Released-CN-Domain					PRESENCE mandatory	},
	...
}

EnhancedRelocationRelease-Extensions RNSAP-PROTOCOL-EXTENSION ::= {
	...
}

-- **************************************************************
--
-- MBSFN MCCH INFORMATION
--
-- **************************************************************

MBSFNMCCHInformation ::= SEQUENCE {
	protocolIEs				ProtocolIE-Container	{{MBSFNMCCHInformation-IEs}},
	protocolExtensions		ProtocolExtensionContainer	{{MBSFNMCCHInformation-Extensions}}		OPTIONAL,
	...
}

MBSFNMCCHInformation-IEs RNSAP-PROTOCOL-IES ::= {
	{ ID id-MBSFN-Cluster-Identity 	CRITICALITY		ignore		TYPE MBSFN-Cluster-Identity PRESENCE	mandatory} |
	{ ID id-MCCH-Message-List 	CRITICALITY		reject		TYPE MCCH-Message-List PRESENCE	mandatory} |
	{ ID id-CFN  CRITICALITY		reject		TYPE CFN PRESENCE	mandatory}|
	{ ID id-MCCH-Configuration-Info			CRITICALITY		ignore		TYPE	MCCH-Configuration-Info				PRESENCE	optional}|
	{ ID id-MBSFN-Scheduling-Transmission-Time-Interval-Info-List 	CRITICALITY		ignore		TYPE MBSFN-Scheduling-Transmission-Time-Interval-Info-List PRESENCE	optional},
	...
}

MBSFNMCCHInformation-Extensions RNSAP-PROTOCOL-EXTENSION ::= {
	...
}

-- **************************************************************
--
-- SECONDARY UL FREQUENCY REPORT
--
-- **************************************************************

SecondaryULFrequencyReport ::= SEQUENCE {
	protocolIEs				ProtocolIE-Container	{{SecondaryULFrequencyReport-IEs}},
	protocolExtensions		ProtocolExtensionContainer	{{SecondaryULFrequencyReport-Extensions}}			OPTIONAL,
	...
}

SecondaryULFrequencyReport-IEs RNSAP-PROTOCOL-IES ::= {
	{ ID id-ActivationInformation 	CRITICALITY		ignore		TYPE ActivationInformation		PRESENCE mandatory },
	...
}

SecondaryULFrequencyReport-Extensions RNSAP-PROTOCOL-EXTENSION ::= {
	...
}

-- **************************************************************
--
-- SECONDARY UL FREQUENCY UPDATE INDICATION
--
-- **************************************************************

SecondaryULFrequencyUpdateIndication ::= SEQUENCE {
	protocolIEs				ProtocolIE-Container	{{SecondaryULFrequencyUpdateIndication-IEs}},
	protocolExtensions		ProtocolExtensionContainer	{{SecondaryULFrequencyUpdateIndication-Extensions}}		OPTIONAL,
	...
}


SecondaryULFrequencyUpdateIndication-IEs RNSAP-PROTOCOL-IES ::= {
	{ ID id-ActivationInformation 	CRITICALITY		ignore		TYPE ActivationInformation		PRESENCE mandatory },
	...
}

SecondaryULFrequencyUpdateIndication-Extensions RNSAP-PROTOCOL-EXTENSION ::= {
	...
}


-- **************************************************************
--
-- PRIVATE MESSAGE
--
-- **************************************************************

PrivateMessage ::= SEQUENCE {
	privateIEs		PrivateIE-Container  {{PrivateMessage-IEs}},
	...
}

PrivateMessage-IEs RNSAP-PRIVATE-IES ::= {
	...
}

END
